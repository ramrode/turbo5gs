-- Generated by closure.py. Do not edit.
-- Self-contained 5G SA subset of 3GPP TS 32.298 CHF CDRs.
-- Definitions marked (trimmed) come from patched/; every other
-- definition is copied verbatim from standard/.

CHFChargingDataTypes {itu-t (0) identified-organization (4) etsi (0) mobileDomain (0) charging (5) chfChargingDataTypes (15) asn1Module (0) version1 (0)}
DEFINITIONS IMPLICIT TAGS	::=

BEGIN

-- [TS32298_CHFChargingDataTypes.asn]
CHFRecord	::= CHOICE 
--
-- Record values 200..201 are specific
--
{
	chargingFunctionRecord			[200] ChargingRecord
}

-- [TS32298_GenericChargingDataTypes.asn]
CallDuration 			::= INTEGER
--
-- The call duration is counted in seconds. 
-- For successful calls /sessions / PDP contexts, this is the chargeable duration.
-- For call attempts this is the call holding time.
-- 

-- [TS32298_GenericChargingDataTypes.asn]
CauseForRecClosing	::= INTEGER
--
-- Cause codes 0 to 15 are defined 'CauseForTerm' (cause for termination)
-- There is no direct correlation between these two types.
--
-- LCS related causes belong to the MAP error causes acc. TS 29.002 [214]
--
-- In PGW-CDR and SGW-CDR the value servingNodeChange is used for partial record
-- generation due to Serving Node Address list Overflow
-- In SGSN servingNodeChange indicates the SGSN change
-- 
-- sWGChange value is used in both the S-GW, TWAG and ePDG for inter serving node change
-- 
{
	normalRelease					(0),
	partialRecord					(1),
	abnormalRelease					(4),
	cAMELInitCallRelease			(5),
	volumeLimit						(16),
	timeLimit						(17),
	servingNodeChange				(18),
	maxChangeCond					(19),
	managementIntervention			(20),
	intraSGSNIntersystemChange		(21),
	rATChange						(22),
	mSTimeZoneChange				(23),
	sGSNPLMNIDChange 				(24),
	sGWChange						(25),
	aPNAMBRChange					(26),
	mOExceptionDataCounterReceipt	(27),
	unauthorizedRequestingNetwork	(52),
	unauthorizedLCSClient			(53),
	positionMethodFailure			(54),
	unknownOrUnreachableLCSClient	(58),
	listofDownstreamNodeChange		(59),
	uSUSatelliteChange				(60),
	uSUGroundFallback				(61)
}

-- [TS32298_GenericChargingDataTypes.asn]
ChargingID	::= INTEGER (0..4294967295)
--
-- Generated in P-GW, part of IP-CAN bearer
-- 0..4294967295 is equivalent to 0..2**32-1
--

-- [(trimmed) chf-5gsa-records.asn]
ChargingRecord 	::= SET
{
	recordType									[0] RecordType,
	recordingNetworkFunctionID					[1] NetworkFunctionName,
	subscriberIdentifier						[2] SubscriptionID OPTIONAL,
	nFunctionConsumerInformation				[3] NetworkFunctionInformation,
	listOfMultipleUnitUsage						[5] SEQUENCE OF MultipleUnitUsage OPTIONAL,
	recordOpeningTime							[6] TimeStamp,
	duration									[7] CallDuration,
	causeForRecClosing							[9] CauseForRecClosing,
	localRecordSequenceNumber					[11] LocalSequenceNumber OPTIONAL,
	pDUSessionChargingInformation				[13] PDUSessionChargingInformation OPTIONAL,
	chargingSessionIdentifier					[16] ChargingSessionIdentifier OPTIONAL
}

-- [TS32298_CHFChargingDataTypes.asn]
ChargingSessionIdentifier	::= OCTET STRING
-- See 3GPP TS 32.290 [57] for details.

-- [TS32298_CHFChargingDataTypes.asn]
DataNetworkNameIdentifier	::= IA5String (SIZE(1..63))
--
-- Network Identifier part of DNN in dot representation.
-- For example, if the complete DNN is 'apn1a.apn1b.apn1c.mnc022.mcc111.gprs'
-- The Identifier is 'apn1a.apn1b.apn1c' and is presented in this form in the CDR.
--

-- [TS32298_GenericChargingDataTypes.asn]
DataVolumeOctets		::= INTEGER
--
-- The volume of data transferred in octets.
--

-- [TS32298_GenericChargingDataTypes.asn]
InvolvedParty ::= CHOICE 
{
	sIP-URI		[0] GraphicString, -- refer to rfc3261 [401]
	tEL-URI		[1] GraphicString,	-- refer to rfc3966 [402]
	uRN			[2] GraphicString,	-- refer to rfc5031 [407]
	iSDN-E164 	[3] GraphicString,	-- refer to ITU-T Recommendation E.164[308]
	externalId 	[4] UTF8String		-- refer to clause 19.7.2 TS 23.003 [200]

}

-- [TS32298_GenericChargingDataTypes.asn]
LocalSequenceNumber ::= INTEGER (0..4294967295)
--
-- Sequence number of the record in this node
-- 0.. 4294967295 is equivalent to 0..2**32-1, unsigned integer in four octets
--

-- [(trimmed) chf-5gsa-records.asn]
MultipleUnitUsage 		::= SEQUENCE
{
	ratingGroup							[0] RatingGroupId,
	usedUnitContainers					[1] SEQUENCE OF UsedUnitContainer OPTIONAL
}

-- [(trimmed) chf-5gsa-records.asn]
NetworkFunctionInformation	::= SEQUENCE
{
	networkFunctionality					[0] NetworkFunctionality,
	networkFunctionName					[1] NetworkFunctionName OPTIONAL
}

-- [TS32298_CHFChargingDataTypes.asn]
NetworkFunctionName	::= IA5String (SIZE(1..36))
-- Shall be a Universally Unique Identifier (UUID) version 4, as described in IETF RFC 4122 [410]

-- [(trimmed) spec-defects.asn]
NetworkFunctionality	::= ENUMERATED
{
	cHF				(0),
	-- CHF is applicable in two scenarios: inter-CHF communication andfailure cases
	sMF				(1),
-- SMF is applicable in two scenarios: as NF consumer of CHF services, and as API Target NF 
-- in NEF charging
	aMF				(2),
-- AMF is applicable in two scenario: as NF consumer of CHF services, and as API Target NF
-- in NEF charging
	sMSF			(3),
	sGW				(4),
	-- SGW is only applicable for interworking with EPC scenario
	-- when UE is connected to P-GW+SMF via EPC
	iSMF			(5),
	ePDG			(6),
	-- ePDG is only applicable for interworking with EPC scenario
	-- when UE is connected to P-GW+SMF via EPC/ePDG
	cEF				(7),
	nEF			(8),
	pGWCSMF			(9),
	mnS-Producer 	(10),
	sGSN			(11),
	-- SGSN is only applicable when UE is connected to SMF+PGW-C via GERAN/UTRAN
	fiveGDDNMF		(12),
	vSMF			(13),
	-- vSMF may be used instead of sMF in roaming scenarios}
	iMS-Node		(14),
	eES				(15),
	mMS-Node		(16),
	pCF				(17),
	-- PCF is applicable only as API Target NF in NEF charging
	uDM				(18),
	-- UDM is applicable only as API Target NF in NEF charging
	uPF				(19),
	-- UPF is applicable only as API Target NF in NEF charging
	tSN-AF			(20),
	tSNTSF			(21),
	mB-SMF			(22),
	aIOTF			(23),
	-- AIOTF is applicable only as API Target NF in NEF charging
	nWDAF			(24)
}

-- [(trimmed) chf-5gsa-records.asn]
PDUSessionChargingInformation 	::= SET
{
	pDUSessionChargingID					[0] ChargingID,
	userIdentifier							[1] InvolvedParty OPTIONAL,
	pDUSessionId							[6] PDUSessionId,
	networkSliceInstanceID					[7] SingleNSSAI OPTIONAL,
	dataNetworkNameIdentifier				[13] DataNetworkNameIdentifier OPTIONAL,
	pDUSessionstartTime						[17] TimeStamp OPTIONAL,
	pDUSessionstopTime						[18] TimeStamp OPTIONAL
}

-- [TS32298_CHFChargingDataTypes.asn]
PDUSessionId 		::= INTEGER (0..255)
-- 
-- See 3GPP TS 29.571 [249] for details
-- 

-- [TS32298_GPRSChargingDataTypes.asn]
RatingGroupId		::= INTEGER
-- 
-- IP service flow identity (DCCA), range of 4 byte (0... 4294967295)
-- see Rating-Group AVP as used in TS 32.299 [50]
--

-- [TS32298_GenericChargingDataTypes.asn]
RecordType 	::= INTEGER 
-- 
--	Record values 0..17 and 87,89  are CS specific. The contents are defined in TS 32.250 [10]
--
{
	moCallRecord			(0),
	mtCallRecord			(1),
	roamingRecord			(2),
	incGatewayRecord		(3),
	outGatewayRecord		(4),
	transitCallRecord		(5),
	moSMSRecord				(6),
	mtSMSRecord				(7),
	moSMSIWRecord			(8),
	mtSMSGWRecord			(9),
	ssActionRecord			(10),
	hlrIntRecord			(11),
	locUpdateHLRRecord		(12),
	locUpdateVLRRecord		(13),
	commonEquipRecord		(14),
	moTraceRecord			(15),	-- used in earlier releases
	mtTraceRecord			(16),	-- used in earlier releases
	termCAMELRecord			(17),
--
--	Record values 18..22 are GPRS specific. The contents are defined in TS 32.251 [11]
--
	sgsnPDPRecord			(18),
	sgsnMMRecord			(20),
	sgsnSMORecord			(21),	-- also MME UE originated SMS record
	sgsnSMTRecord			(22),	-- also MME UE terminated SMS record
-- 
--  Record values 23..25 are CS-LCS specific. The contents are defined in TS 32.250 [10]
--
	mtLCSRecord				(23),
	moLCSRecord				(24),
	niLCSRecord				(25),
-- 
--  Record values 26..28 are GPRS-LCS specific. The contents are defined in TS 32.251 [11]
--
	sgsnMTLCSRecord			(26),
	sgsnMOLCSRecord			(27),
	sgsnNILCSRecord			(28),
--
--  Record values 30..62 are MMS specific. The contents are defined in TS 32.270 [30]
--
	mMO1SRecord				(30),
	mMO4FRqRecord			(31),
	mMO4FRsRecord			(32),
	mMO4DRecord				(33),
	mMO1DRecord				(34),
	mMO4RRecord				(35),
	mMO1RRecord				(36),
	mMOMDRecord				(37),
	mMR4FRecord				(38),
	mMR1NRqRecord			(39),
	mMR1NRsRecord			(40),
	mMR1RtRecord			(41),
	mMR1AFRecord			(42),
	mMR4DRqRecord			(43),
	mMR4DRsRecord			(44),
	mMR1RRRecord			(45),
	mMR4RRqRecord			(46),
	mMR4RRsRecord			(47),
	mMRMDRecord				(48),
	mMFRecord				(49),
	mMBx1SRecord			(50),
	mMBx1VRecord			(51),
	mMBx1URecord			(52),
	mMBx1DRecord			(53),
	mM7SRecord				(54),
	mM7DRqRecord			(55),
	mM7DRsRecord			(56),
	mM7CRecord				(57),
	mM7RRecord				(58),
	mM7DRRqRecord			(59),
	mM7DRRsRecord			(60),
	mM7RRqRecord			(61),
	mM7RRsRecord			(62),
--
--  Record values 63..70, 82, 89..91 are IMS specific.
--  The contents are defined in TS 32.260 [20]
--
	sCSCFRecord				(63),
	pCSCFRecord				(64),
	iCSCFRecord				(65),
	mRFCRecord				(66),
	mGCFRecord				(67),
	bGCFRecord				(68),
	aSRecord				(69),
	eCSCFRecord				(70),
	iBCFRecord				(82),
	tRFRecord				(89),
	tFRecord				(90),
aTCFRecord				(91),
--
--  Record values 71..75 are LCS specific. The contents are defined in TS 32.271 [31]
--
	lCSGMORecord			(71),
	lCSRGMTRecord			(72),
	lCSHGMTRecord			(73),
	lCSVGMTRecord			(74),
	lCSGNIRecord			(75),
--
--  Record values 76..79,86 are MBMS specific.
--  The contents are defined in TS 32.251 [11] and TS 32.273 [33]
--
--  Record values 76,77 and 86 are MBMS bearer context specific
--
	sgsnMBMSRecord			(76),
	ggsnMBMSRecord			(77), 
	gwMBMSRecord			(86),
--
--  Record values 78 and 79 are MBMS service specific and defined in TS 32.273 [33]
--
	sUBBMSCRecord			(78),
	cONTENTBMSCRecord		(79),
--
--  Record Values 80..81 are PoC specific. The contents are defined in TS 32.272 [32]
--
	pPFRecord				(80),
	cPFRecord				(81),
--  
--	Record values 84,85 and 92,95,96, 97 are EPC specific.
--  The contents are defined in TS 32.251 [11]
--
	sGWRecord				(84),
	pGWRecord				(85),
	tDFRecord				(92),
	iPERecord				(95),
	ePDGRecord				(96),
	tWAGRecord				(97),
--
--  Record Value 83 is MMTel specific. The contents are defined in TS 32.275 [35]
--
	mMTelRecord				(83),
--
--  Record value  87,88 and 89 are CS specific. The contents are defined in TS 32.250 [10]
--
	mSCsRVCCRecord			(87),
	mMTRFRecord				(88),
	iCSRegisterRecord		(99),
--
--  Record values 93 and 94 are SMS specific. The contents are defined in TS 32.274 [34]
--
	sCSMORecord				(93),
	sCSMTRecord				(94),
--
--  Record values 100, 101 and 102 are ProSe specific. The contents are defined in TS 32.277 [36]
--
	pFDDRecord				(100),
	pFEDRecord				(101),
	pFDCRecord				(102),
--
--  Record values103 and 104 are Monitoring Event specific. The contents are defined in TS 
--	32.278 [38]
--
	mECORecord				(103),
	mERERecord				(104),
--
--  Record values 105 to 106 are CP data transfer specific. The contents are defined in TS 
--	32.253 [13]
--
	cPDTSCERecord			(105),
	cPDTSNNRecord			(106), --
--  Record values 110 to 113 are SMS specific. The contents are defined in TS 
--	32.274 [34]
--
	sCDVTT4Record			(110),
	sCSMOT4Record			(111),
	iSMSMORecord			(112),
	iSMSMTRecord			(113),
--  
--  Record values 120 are Exposure Function API specific. The contents are defined in TS 
--	32.254 [14]
--
	eASCERecord				(120),
--
--  Record values from 200 are specific to Charging Function domain 
--
	chargingFunctionRecord		(200)
--


}

-- [TS32298_GPRSChargingDataTypes.asn]
ServiceIdentifier	::= INTEGER (0..4294967295)
--
-- The service identifier is used to identify the service or the service component
-- the service data flow relates to. See Service-Identifier AVP as defined in TS 29.212 [220]
--

-- [TS32298_CHFChargingDataTypes.asn]
SingleNSSAI	::= SEQUENCE
-- See S-NSSAI subclause 28.4.2 of TS 23.003 [200] for encoding.
{
	sST			[0] SliceServiceType,
	sD 			[1] SliceDifferentiator OPTIONAL
}

-- [TS32298_CHFChargingDataTypes.asn]
SliceDifferentiator		::= OCTET STRING (SIZE(3))
--
-- See subclause 28.4.2 TS 23.003 [200]
--

-- [TS32298_CHFChargingDataTypes.asn]
SliceServiceType ::= INTEGER (0..255)
--
-- See subclause 28.4.2 TS 23.003 [200]
--

-- [TS32298_GenericChargingDataTypes.asn]
SubscriptionID	::= SET
--
-- See TS 23.003 [200] and TS 29.571 [249]
--
{
	subscriptionIDType	[0]	SubscriptionIDType,
	subscriptionIDData	[1]	UTF8String
}

-- [TS32298_GenericChargingDataTypes.asn]
SubscriptionIDType	::= ENUMERATED
{
	eND-USER-E164		(0),
	eND-USER-IMSI		(1),
	eND-USER-SIP-URI		(2),
	eND-USER-NAI			(3),
	eND-USER-PRIVATE		(4)

--
-- eND-USER-NAI can be used for externalIdentifier.
-- eND-USER-IMSI can be used for 5G BRG or 5G CRG.
-- eND-USER-NAI can be used for GLI or GCI for wireline access network scenarios
-- NAI format for GCI and GLI is specified in 28.15.5 and 28.15.6 of TS 23.003 [200]. 
--

}

-- [TS32298_GenericChargingDataTypes.asn]
TimeStamp	::= OCTET STRING (SIZE(9))
--
-- The contents of this field are a compact form of the UTCTime format
-- containing local time plus an offset to universal time. Binary coded
-- decimal encoding is employed for the digits to reduce the storage and
-- transmission overhead
-- e.g. YYMMDDhhmmssShhmm
-- where
-- YY 	= 	Year 00 to 99		BCD encoded
-- MM 	= 	Month 01 to 12 		BCD encoded
-- DD	=	Day 01 to 31		BCD encoded
-- hh	=	hour 00 to 23		BCD encoded
-- mm	=	minute 00 to 59		BCD encoded
-- ss	=	second 00 to 59		BCD encoded
-- S	=	Sign 0 = "+", "-"	ASCII encoded
-- hh	=	hour 00 to 23		BCD encoded
-- mm	=	minute 00 to 59		BCD encoded
--

-- [(trimmed) chf-5gsa-records.asn]
UsedUnitContainer 		::= SEQUENCE
{
	serviceIdentifier					[0] ServiceIdentifier OPTIONAL,
	time								[1] CallDuration OPTIONAL,
	dataTotalVolume						[4] DataVolumeOctets OPTIONAL,
	dataVolumeUplink					[5] DataVolumeOctets OPTIONAL,
	dataVolumeDownlink					[6] DataVolumeOctets OPTIONAL,
	localSequenceNumber					[9] LocalSequenceNumber OPTIONAL
}

END
