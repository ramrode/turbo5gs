CHFChargingDataTypes {itu-t (0) identified-organization (4) etsi (0) mobileDomain (0) charging (5) chfChargingDataTypes (15) asn1Module (0) version1 (0)}
DEFINITIONS IMPLICIT TAGS	::=

BEGIN

-- EXPORTS everything 

IMPORTS	

CallDuration,
CauseForRecClosing,
ChargingID,
DataVolumeOctets,
Diagnostics,
Ecgi,
EnhancedDiagnostics,
DynamicAddressFlag,
InvolvedParty,
IPAddress,
LCSClientIdentity,
LocalSequenceNumber,
ManagementExtensions,
MessageClass,
MessageReference,
MSCAddress,
MSISDN,
MSTimeZone,
Ncgi,
Nid,
NodeAddress,
PLMN-Id,
PositioningData,
PriorityType,
PSCellInformation,
RANNASCause,
RecordType,
ServiceSpecificInfo,
Session-Id,
SubscriberEquipmentNumber,
SubscriptionID,
ThreeGPPPSDataOffStatus,
TimeStamp,
TMGI
FROM GenericChargingDataTypes {itu-t (0) identified-organization (4) etsi(0) mobileDomain (0) charging (5) genericChargingDataTypes (0) asn1Module (0) version2 (1)}

AddressString,
IMSI
FROM MAP-CommonDataTypes {itu-t identified-organization (4) etsi (0) mobileDomain (0) gsm-Network (1) modules (3) map-CommonDataTypes (18) version21 (21)}

CalleePartyInformation,
ChargingCharacteristics,
ChargingRuleBaseName,
ChChSelectionMode,
EventBasedChargingInformation,
PresenceReportingAreaInfo,
RatingGroupId,
ServiceIdentifier
FROM GPRSChargingDataTypes {itu-t (0) identified-organization (4) etsi (0) mobileDomain (0) charging (5) gprsChargingDataTypes (2) asn1Module (0) version2 (1)}

OriginatorInfo,
RecipientInfo,
RecipientAddress,
SMAddressInfo,
SMMessageType,
SMSResult,
SMSStatus
FROM SMSChargingDataTypes {itu-t (0) identified-organization (4) etsi(0) mobileDomain (0) charging (5)  smsChargingDataTypes (10) asn1Module (0) version2 (1)}

APIDirection
FROM ExposureFunctionAPIChargingDataTypes {itu-t (0) identified-organization (4) etsi (0) mobileDomain (0) charging (5) exposureFunctionAPIChargingDataTypes (14) asn1Module (0) version2 (1)}

SupplService
FROM MMTelChargingDataTypes {itu-t (0) identified-organization (4) etsi(0) mobileDomain (0) charging (5) mMTelChargingDataTypes (9) asn1Module (0) version2 (1)}


AccessNetworkInfoChange,
AccessTransferInformation,
ApplicationServersInformation,
CalledIdentityChange,
CarrierSelectRouting,
Early-Media-Components-List,
FEIdentifierList,
IMS-Charging-Identifier,
IMSCommunicationServiceIdentifier,
InterOperatorIdentifiers,
ISUPCause,
ListOfInvolvedParties,
ListOfReasonHeader,
MessageBody,
NNI-Information,
NumberPortabilityRouting,
Role-of-Node,
S-CSCF-Information,
SDP-Media-Component,
ServedPartyIPAddress,
Service-Id,
SessionPriority,
SIP-Method,
TADIdentifier,
TransitIOILists,
TransmissionMedium,
TrunkGroupID
FROM IMSChargingDataTypes {itu-t (0) identified-organization (4) etsi(0) mobileDomain (0) charging (5) imsChargingDataTypes (4) asn1Module (0) version2 (1)}

AppSpecificData,
ProseFunctionality,
ProSeEventType,
ProSeUERole,
RangeClass,
ProximityAlertIndication,
ChangeOfProSeCondition,
CoverageInfo,
RadioParameterSetInfo,
TransmitterInfo
FROM ProSeChargingDataTypes {itu-t (0) identified-organization (4) etsi (0) mobileDomain (0) charging (5) proseChargingDataTypes (11) asn1Module (0) version2 (1)}
;

--
--  CHF RECORDS
--

CHFRecord	::= CHOICE 
--
-- Record values 200..201 are specific
--
{
	chargingFunctionRecord			[200] ChargingRecord
}

ChargingRecord 	::= SET
{
	recordType									[0] RecordType,
	recordingNetworkFunctionID					[1] NetworkFunctionName,
	subscriberIdentifier						[2] SubscriptionID OPTIONAL,
	nFunctionConsumerInformation				[3] NetworkFunctionInformation,
	triggers									[4] SEQUENCE OF Trigger OPTIONAL,
	listOfMultipleUnitUsage						[5] SEQUENCE OF MultipleUnitUsage OPTIONAL,
	recordOpeningTime							[6] TimeStamp,
	duration									[7] CallDuration,
	recordSequenceNumber						[8] INTEGER OPTIONAL,
	causeForRecClosing							[9] CauseForRecClosing,
	diagnostics									[10] Diagnostics OPTIONAL,
	localRecordSequenceNumber					[11] LocalSequenceNumber OPTIONAL,
	recordExtensions							[12] ManagementExtensions OPTIONAL,
	pDUSessionChargingInformation				[13] PDUSessionChargingInformation OPTIONAL,
	roamingQBCInformation						[14] RoamingQBCInformation OPTIONAL,
	sMSChargingInformation						[15] SMSChargingInformation OPTIONAL,
	chargingSessionIdentifier					[16] ChargingSessionIdentifier OPTIONAL,
	serviceSpecificationInformation				[17] OCTET STRING OPTIONAL,
	exposureFunctionAPIInformation				[18] ExposureFunctionAPIInformation OPTIONAL,
	registrationChargingInformation				[19] RegistrationChargingInformation OPTIONAL,
	n2ConnectionChargingInformation				[20] N2ConnectionChargingInformation OPTIONAL,
	locationReportingChargingInformation		[21] LocationReportingChargingInformation OPTIONAL,
	incompleteCDRIndication						[22] IncompleteCDRIndication OPTIONAL,
	tenantIdentifier							[23] TenantIdentifier OPTIONAL,
	mnSConsumerIdentifier						[24] MnSConsumerIdentifier OPTIONAL,
	nSMChargingInformation						[25] NSMChargingInformation OPTIONAL,
	nSPAChargingInformation						[26] NSPAChargingInformation OPTIONAL,
	chargingID									[27] ChargingID OPTIONAL,
	iMSChargingInformation						[28] IMSChargingInformation OPTIONAL,
	mMTelChargingInformation					[29] MMTelChargingInformation OPTIONAL,
	edgeInfrastructureUsageChargingInformation	[30] EdgeInfrastructureUsageChargingInformation OPTIONAL,
	eASDeploymentChargingInformation			 [31] EASDeploymentChargingInformation OPTIONAL,
	directEdgeEnablingServiceChargingInformation	[32] ExposureFunctionAPIInformation OPTIONAL,
	exposedEdgeEnablingServiceChargingInformation	[33] ExposureFunctionAPIInformation OPTIONAL,
	proseChargingInformation 					[34] ProseChargingInformation OPTIONAL,
	eASID										[35] UTF8String OPTIONAL,
	eDNID							 			[36] UTF8String OPTIONAL,
	eASProviderIdentifier						[37] UTF8String OPTIONAL,
	mMSChargingInformation						[38] MMSChargingInformation OPTIONAL,
	aMFIdentifier								[39] AMFID OPTIONAL,
	invocationTimestamp							[40] TimeStamp OPTIONAL,
	nSACFChargingInformation					[41] NSACFChargingInformation OPTIONAL,
	tSNChargingInformation					[42] TSNChargingInformation OPTIONAL,
	mBSSessionChargingInformation				[43] MbsSessionChargingInformation OPTIONAL,
	interCHFInformation							[44] InterCHFInformation OPTIONAL,
	nSSAAChargingInformation					[45] NSSAAChargingInformation OPTIONAL,
	rangingSLChargingInformation				[46] RangingSLChargingInformation OPTIONAL,
	lCSInformation								[47] LCSInformation OPTIONAL,
	networkSharingChargingInformation			[48] NetworkSharingChargingInformation OPTIONAL

}

--
-- PDU Session Charging Information
--

PDUSessionChargingInformation 	::= SET
{
	pDUSessionChargingID					[0] ChargingID,
	userIdentifier							[1] InvolvedParty OPTIONAL,
	userEquipmentInfo						[2] SubscriberEquipmentNumber OPTIONAL,
	userLocationInformation					[3] UserLocationInformation OPTIONAL,
	userRoamerInOut							[4] RoamerInOut OPTIONAL,
	presenceReportingAreaInfo				[5]	PresenceReportingAreaInfo OPTIONAL,
	pDUSessionId							[6] PDUSessionId,
	networkSliceInstanceID					[7] SingleNSSAI OPTIONAL,
	pDUType									[8] PDUSessionType OPTIONAL,
	sSCMode									[9] SSCMode OPTIONAL,
	sUPIPLMNIdentifier						[10] PLMN-Id OPTIONAL,
	servingNetworkFunctionID				[11] SEQUENCE OF ServingNetworkFunctionID OPTIONAL,
	rATType									[12] RATType OPTIONAL,
	dataNetworkNameIdentifier				[13] DataNetworkNameIdentifier OPTIONAL,
	pDUAddress								[14] PDUAddress OPTIONAL,
	authorizedQoSInformation				[15] AuthorizedQoSInformation OPTIONAL,
	uETimeZone 								[16] MSTimeZone OPTIONAL,
	pDUSessionstartTime						[17] TimeStamp OPTIONAL,
	pDUSessionstopTime						[18] TimeStamp OPTIONAL,
	diagnostics								[19] Diagnostics OPTIONAL,
	chargingCharacteristics					[20] ChargingCharacteristics OPTIONAL,
	chChSelectionMode						[21] ChChSelectionMode OPTIONAL,
	threeGPPPSDataOffStatus						[22] ThreeGPPPSDataOffStatus OPTIONAL,
	rANSecondaryRATUsageReport 				[23] SEQUENCE OF NGRANSecondaryRATUsageReport OPTIONAL,
	subscribedQoSInformation 				[24] SubscribedQoSInformation OPTIONAL,
	authorizedSessionAMBR 					[25] SessionAMBR OPTIONAL,
	subscribedSessionAMBR 					[26] SessionAMBR OPTIONAL,
	servingCNPLMNID							[27] PLMN-Id OPTIONAL,
	sUPIunauthenticatedFlag 				[28] NULL OPTIONAL,
	dnnSelectionMode						[29] DNNSelectionMode OPTIONAL,
	homeProvidedChargingID					[30] ChargingID OPTIONAL,
	mAPDUNonThreeGPPUserLocationInfo		[31] UserLocationInformation OPTIONAL,
	mAPDUNonThreeGPPRATType					[32] RATType OPTIONAL,
	mAPDUSessionInformation					[33] MAPDUSessionInformation OPTIONAL,
	enhancedDiagnostics						[34] EnhancedDiagnostics5G OPTIONAL,
	userLocationInformationASN1				[35] UserLocationInformationStructured OPTIONAL,
	mAPDUNonThreeGPPUserLocationInfoASN1	[36] UserLocationInformationStructured OPTIONAL,
	userLocationTime						[37] TimeStamp OPTIONAL, -- not to be used
-- user location info time is included under UserLocationInformation
	mAPDUNonThreeGPPUserLocationTime		[38] TimeStamp OPTIONAL,
	listOfPresenceReportingAreaInformation	[39] SEQUENCE OF PresenceReportingAreaInfo OPTIONAL,
	redundantTransmissionType				[40] RedundantTransmissionType OPTIONAL,
	pDUSessionPairID						[41] PDUSessionPairID OPTIONAL,
	fiveGLANTypeService						[42] FiveGLANTypeService OPTIONAL,
	cpCIoTOptimisationIndicator				[43] TimeStamp OPTIONAL,
	fiveGSControlPlaneOnlyIndicator			[44] QosMonitoringReport OPTIONAL,
	smfChargingID							[45] UTF8String OPTIONAL,
	smfHomeProvidedChargingID				[46] UTF8String OPTIONAL,
	sNPNInformation							[47] SNPNInformation OPTIONAL,
	hPLMNSNSSAI								[48] SingleNSSAI OPTIONAL,
	iMSSessionInformation					[49] IMSSessionInformation OPTIONAL,
	alternativeSNSSAI						[50] SingleNSSAI OPTIONAL,
	fiveGSBridgeInformation					[51] FiveGSBridgeInformation OPTIONAL,
	fiveGMulticastService					[52] FiveGMulticastService OPTIONAL,
	satelliteAccessIndicator				[53] BOOLEAN OPTIONAL,
	satelliteBackhaulInformation			[54] SatelliteBackhaulInformation OPTIONAL,
	serviceLevelAA							[55] UTF8String OPTIONAL,
	userDisasterRoamingInd					[56] BOOLEAN OPTIONAL,
	NonThreeGPPUserLocationTime				[57] TimeStamp OPTIONAL

}

--
-- Roaming QBC Information

--

RoamingQBCInformation 	::= SET
{
	multipleQFIcontainer			[0] SEQUENCE OF MultipleQFIContainer OPTIONAL,
	uPFID							[1] NetworkFunctionName OPTIONAL,
									-- included for backwards compatibility and
									-- can be included based on operators requirement
	roamingChargingProfile			[2] RoamingChargingProfile OPTIONAL
}


--
-- SMS Charging Information
--

SMSChargingInformation	::= SET
{
	originatorInfo				[1] OriginatorInfo OPTIONAL,
	recipientInfos				[2] SEQUENCE OF RecipientInfo OPTIONAL,
	userEquipmentInfo			[3] SubscriberEquipmentNumber OPTIONAL,
	userLocationInformation		[4] UserLocationInformation OPTIONAL,
	uETimeZone 					[5] MSTimeZone OPTIONAL,
	rATType						[6] RATType OPTIONAL,
	sMSCAddress					[7] AddressString OPTIONAL,
	eventtimestamp				[8] TimeStamp,
-- 9 to 19 is for future use
	sMDataCodingScheme			[20] INTEGER OPTIONAL,
	sMMessageType				[21] SMMessageType OPTIONAL,
	sMReplyPathRequested			[22] SMReplyPathRequested OPTIONAL,
	sMUserDataHeader				[23] OCTET STRING OPTIONAL,
	sMSStatus					[24] SMSStatus OPTIONAL,
	sMDischargeTime				[25] TimeStamp OPTIONAL,
	sMTotalNumber 				[26] INTEGER OPTIONAL,
	sMServiceType				[27] SMServiceType OPTIONAL,
	sMSequenceNumber 			[28] INTEGER OPTIONAL,
	sMSResult					[29] SMSResult OPTIONAL,
	submissionTime				[30] TimeStamp OPTIONAL,
	sMPriority					[31] PriorityType OPTIONAL,
	messageReference				[32] MessageReference OPTIONAL,
	messageSize					[33] INTEGER OPTIONAL,
	messageClass					[34] MessageClass OPTIONAL,
	sMdeliveryReportRequested	[35] SMdeliveryReportRequested OPTIONAL,
	messageClassTokenText		[36] UTF8String OPTIONAL,
	userRoamerInOut				[37] RoamerInOut OPTIONAL,
	userLocationInformationASN1	[38] UserLocationInformationStructured OPTIONAL

}


--
-- Exposure Function API Information corresponds to NEF API Charging information
--

ExposureFunctionAPIInformation	::= SET
{
	groupIdentifier					[0] UTF8String OPTIONAL,
-- This UTF8String is based on the string specified in TS 29.571 [249]
-- The string may also be based on AddressString.
	aPIDirection					[1] APIDirection OPTIONAL,
	aPITargetNetworkFunction		[2] NetworkFunctionInformation OPTIONAL,
	aPIResultCode					[3] APIResultCode OPTIONAL,
	aPIName							[4] IA5String,
	aPIReference					[5] IA5String OPTIONAL,
	aPIContent						[6] OCTET STRING OPTIONAL,
	externalIndividualIdentifier	[7] InvolvedParty OPTIONAL,
	externalGroupIdentifier			[8] ExternalGroupIdentifier OPTIONAL,
	internalGroupIdentifier			[9] InternalGroupIdentifier OPTIONAL,
	internalIndividualIdentifier	[10] SubscriptionID OPTIONAL,
	aPIOperation					[11] APIOperation OPTIONAL,
	externalIndividualIdList		[12] SEQUENCE OF ExternalGroupIdentifier OPTIONAL,
-- externalIndividualIdList [12] field is replaced by externalIndIdList [14]
	internalIndividualIdList		[13] SEQUENCE OF SubscriptionID OPTIONAL,
	externalIndIdList				[14] SEQUENCE OF InvolvedParty OPTIONAL

}


--
-- Registration Charging Information
--

RegistrationChargingInformation 	::= SET
{
	registrationMessagetype				[0] RegistrationMessageType,
	userIdentifier						[1] InvolvedParty OPTIONAL,
	userEquipmentInfo					[2] SubscriberEquipmentNumber OPTIONAL,
	sUPIunauthenticatedFlag 				[3] NULL OPTIONAL,
	userRoamerInOut						[4] RoamerInOut OPTIONAL,
	userLocationInformation				[5] UserLocationInformation OPTIONAL,
	userLocationInfoTime					[6] TimeStamp OPTIONAL, -- This field is not used
-- user location info time is included under UserLocationInformation
	uETimeZone 							[7] MSTimeZone OPTIONAL,
	rATType								[8] RATType OPTIONAL,
	mICOModeIndication					[9] MICOModeIndication OPTIONAL,
	smsIndication						[10] SmsIndication OPTIONAL,
	taiList								[11] SEQUENCE OF TAI OPTIONAL,
	serviceAreaRestriction				[12] ServiceAreaRestriction OPTIONAL,
	requestedNSSAI						[13] SEQUENCE OF SingleNSSAI OPTIONAL,
	allowedNSSAI							[14] SEQUENCE OF SingleNSSAI OPTIONAL,
	rejectedNSSAI						[15] SEQUENCE OF SingleNSSAI OPTIONAL,
	pSCellInformation					[16] PSCellInformation OPTIONAL,
	fiveGMMCapability					[17] FiveGMMCapability OPTIONAL,
	nSSAIMapList							[18] SEQUENCE OF NSSAIMap OPTIONAL,
	amfUeNgapId							[19] AmfUeNgapId OPTIONAL, 
	ranUeNgapId							[20] RanUeNgapId OPTIONAL, 
	ranNodeId							[21] GlobalRanNodeId OPTIONAL,
	userLocationInformationASN1			[22] UserLocationInformationStructured OPTIONAL,
	sNPNID								[23] PlmnIdNid OPTIONAL,
	aMFIdentifier						[24] AMFID OPTIONAL,
	cAGIDList							[25] SEQUENCE OF CagId OPTIONAL,
	alternativeNSSAIMap					[26] SEQUENCE OF AlternativeNSSAIMap OPTIONAL,
	satelliteAccessIndicator			[27] BOOLEAN OPTIONAL,
	serviceLevelAA						[28] UTF8String OPTIONAL,
	userDisasterRoamingInd				[29] BOOLEAN OPTIONAL

}

--
-- N2 connection charging Information 
--

N2ConnectionChargingInformation 	::= SET
{
	n2ConnectionMessageType				[0] N2ConnectionMessageType,
	userIdentifier						[1] InvolvedParty OPTIONAL,
	userEquipmentInfo					[2] SubscriberEquipmentNumber OPTIONAL,
	sUPIunauthenticatedFlag 				[3] NULL OPTIONAL,
	userRoamerInOut						[4] RoamerInOut OPTIONAL,
	userLocationInformation				[5] UserLocationInformation OPTIONAL,
	userLocationInfoTime					[6] TimeStamp OPTIONAL, -- This field is not used
-- user location info time is included under UserLocationInformation
	uETimeZone 							[7] MSTimeZone OPTIONAL,
	rATType								[8] RATType OPTIONAL,
	ranUeNgapId							[9] RanUeNgapId OPTIONAL, 
	ranNodeId							[10] GlobalRanNodeId OPTIONAL,
	restrictedRatList					[11] SEQUENCE OF RATType OPTIONAL,
	forbiddenAreaList					[12] SEQUENCE OF Area OPTIONAL,
	serviceAreaRestriction				[13] ServiceAreaRestriction OPTIONAL,
	restrictedCnList						[14] SEQUENCE OF CoreNetworkType OPTIONAL,
	allowedNSSAI							[15] SEQUENCE OF SingleNSSAI OPTIONAL,
	rrcEstablishmentCause				[16] RrcEstablishmentCause OPTIONAL,
	pSCellInformation					[17] PSCellInformation OPTIONAL,
	amfUeNgapId							[18] AmfUeNgapId OPTIONAL,
	userLocationInformationASN1			[19] UserLocationInformationStructured OPTIONAL,
	nSSAIMapList						[20] SEQUENCE OF NSSAIMap OPTIONAL,
	aMFIdentifier						[21] AMFID OPTIONAL,
	satelliteAccessIndicator			[22] BOOLEAN OPTIONAL



}


--
-- Location reporting charging Information
--


LocationReportingChargingInformation 	::= SET
{
	locationReportingMessagetype			[0] LocationReportingMessageType,
	userIdentifier						[1] InvolvedParty OPTIONAL,
	userEquipmentInfo					[2] SubscriberEquipmentNumber OPTIONAL,
	sUPIunauthenticatedFlag 				[3] NULL OPTIONAL,
	userRoamerInOut						[4] RoamerInOut OPTIONAL,
	userLocationInformation				[5] UserLocationInformation OPTIONAL,
	userLocationInfoTime					[6] TimeStamp OPTIONAL, -- This field is not used
-- user location info time is included under UserLocationInformation
	uETimeZone 							[7] MSTimeZone OPTIONAL,
	presenceReportingAreaInfo			[8]	PresenceReportingAreaInfo OPTIONAL,
	rATType								[9] RATType OPTIONAL,
	pSCellInformation					[10] PSCellInformation OPTIONAL,
	userLocationInformationASN1			[11] UserLocationInformationStructured OPTIONAL,
	listOfPresenceReportingAreaInformation	[12] SEQUENCE OF PresenceReportingAreaInfo OPTIONAL,
	aMFIdentifier						[13] AMFID OPTIONAL,
	satelliteAccessIndicator			[14] BOOLEAN OPTIONAL



}


--
-- Network Slice Performance and Analytics charging Information
--

NSPAChargingInformation			::= SET
{
	singelNSSAI					[0] SingleNSSAI
}

--
-- Network Sharing charging Information
--

NetworkSharingChargingInformation			::= SET
{
	plmnId						[0] PLMN-Id,
	singelNSSAI					[1] SingleNSSAI OPTIONAL
}

--
-- NSM charging Information
--
--
-- See TS 28.541 [254] for more information
--


NSMChargingInformation 	::= SET
{
	managementOperation						[0] ManagementOperation OPTIONAL,
	iDnetworkSliceInstance					[1] OCTET STRING OPTIONAL,
	listOfserviceProfileChargingInformation	[2] SEQUENCE OF ServiceProfileChargingInformation OPTIONAL,
	managementOperationStatus				[3]	ManagementOperationStatus OPTIONAL,
	operationalState							[4]	OperationalState OPTIONAL,
	administrativeState						[5]	AdministrativeState OPTIONAL


}


--
-- MMTel charging Information
--
--
-- See TS 32.275 [35] for more information
--


MMTelChargingInformation	::= SET
{
	supplementaryServices			[0] SEQUENCE OF SupplService OPTIONAL
}


--
-- IMS charging Information
--
--
-- See TS 32.260 [20] for more information
--


IMSChargingInformation	::= SET
{
	eventType								[0] SIPEventType OPTIONAL,
	iMSNodeFunctionality					[1] IMSNodeFunctionality OPTIONAL,
	roleOfNode								[2] Role-of-Node OPTIONAL,
	userIdentifier							[3] InvolvedParty OPTIONAL,
	userEquipmentInfo						[4] SubscriberEquipmentNumber OPTIONAL,
	userLocationInfo						[5] UserLocationInformation OPTIONAL,
	ueTimeZone								[6] MSTimeZone OPTIONAL,
	threeGPPPSDataOffStatus					[7] ThreeGPPPSDataOffStatus OPTIONAL,
	iSUPCause								[8] ISUPCause OPTIONAL,
	controlPlaneAddress						[9] NodeAddress OPTIONAL,
	vlrNumber								[10] MSCAddress OPTIONAL,
	mscAddress								[11] MSCAddress OPTIONAL,
	userSessionID							[12] Session-Id OPTIONAL,
	outgoingSessionID						[13] Session-Id OPTIONAL,
	sessionPriority							[14] SessionPriority OPTIONAL,
	callingPartyAddresses					[15] ListOfInvolvedParties OPTIONAL,
	calledPartyAddress						[16] InvolvedParty OPTIONAL,
	numberPortabilityRouting				[17] NumberPortabilityRouting OPTIONAL,
	carrierSelectRoutingInformation			[18] CarrierSelectRouting OPTIONAL,
	alternateChargedPartyAddress			[19] UTF8String OPTIONAL,
	requestedPartyAddresses					[20] ListOfInvolvedParties OPTIONAL,
	calledAssertedIdentities				[21] ListOfInvolvedParties OPTIONAL,
	calledIdentityChanges					[22] SEQUENCE OF CalledIdentityChange OPTIONAL,
	associatedURIs							[23] ListOfInvolvedParties OPTIONAL,
	timeStamps								[24] TimeStamp OPTIONAL,
	applicationServerInformation			[25] SEQUENCE OF ApplicationServersInformation OPTIONAL,
	interOperatorIdentifiers				[26] SEQUENCE OF InterOperatorIdentifiers OPTIONAL,
	imsChargingIdentifier					[27] IMS-Charging-Identifier OPTIONAL,
	relatedICID								[28] IMS-Charging-Identifier OPTIONAL,
	relatedICIDGenerationNode				[29] NodeAddress OPTIONAL,
	transitIOIList							[30] TransitIOILists OPTIONAL,
	earlyMediaDescription					[31] SEQUENCE OF Early-Media-Components-List OPTIONAL,
	sdpSessionDescription					[32] SEQUENCE OF UTF8String OPTIONAL,
	sdpMediaComponent						[33] SEQUENCE OF SDP-Media-Component OPTIONAL,
	servedPartyIPAddress					[34] ServedPartyIPAddress OPTIONAL,
	serverCapabilities						[35] S-CSCF-Information OPTIONAL,
	trunkGroupID							[36] TrunkGroupID OPTIONAL,
	bearerService							[37] TransmissionMedium OPTIONAL,
	imsServiceId							[38] Service-Id OPTIONAL,
	messageBodies							[39] SEQUENCE OF MessageBody OPTIONAL,
	accessNetworkInformation				[40] SEQUENCE OF UTF8String OPTIONAL,
	additionalAccessNetworkInformation		[41] UTF8String OPTIONAL,
	cellularNetworkInformation				[42] UTF8String OPTIONAL,
	accessTransferInformation				[43] SEQUENCE OF AccessTransferInformation OPTIONAL,
	accessNetworkInfoChange					[44] SEQUENCE OF AccessNetworkInfoChange OPTIONAL,
	imsCommunicationServiceID				[45] IMSCommunicationServiceIdentifier OPTIONAL,
	imsApplicationReferenceID				[46] UTF8String OPTIONAL,
	causeCode								[47] INTEGER OPTIONAL,
	reasonHeaders							[48] ListOfReasonHeader OPTIONAL,
	initialIMSChargingIdentifier			[49] IMS-Charging-Identifier OPTIONAL,
	nniInformation							[50] SEQUENCE OF NNI-Information OPTIONAL,
	fromAddress								[51] UTF8String OPTIONAL,
	imsEmergencyIndicator					[52] NULL OPTIONAL,
	imsVisitedNetworkIdentifier				[53] UTF8String OPTIONAL,
	sipRouteHeaderReceived					[54] UTF8String OPTIONAL,
	sipRouteHeaderTransmitted				[55] UTF8String OPTIONAL,
	tadIdentifier							[56] TADIdentifier OPTIONAL,
	feIdentifierList						[57] FEIdentifierList OPTIONAL,
	imsDCAppInfo							[58] IMSDCAppInfo OPTIONAL,
	mediaResource							[59] MediaResource OPTIONAL,
	satelliteIDList							[110] SEQUENCE OF SatelliteID OPTIONAL,
	involvedPartysatelliteID				[111] InvolvedPartySatelliteID OPTIONAL
}


--
-- Edge Enabling Infrastructure Resource Usage Charging Information
--

EdgeInfrastructureUsageChargingInformation	::= SET
{
	meanVirtualCPUUsage				[0] REAL OPTIONAL,
	meanVirtualMemoryUsage			[1] REAL OPTIONAL,
	meanVirtualDiskUsage			[2] REAL OPTIONAL,
	durationStartTime				[3] TimeStamp OPTIONAL,
	durationEndTime					[4] TimeStamp OPTIONAL,
	measuredInBytes					[5]	INTEGER OPTIONAL,
	measuredOutBytes				[6]	INTEGER OPTIONAL
}

--
-- EAS Deployment Charging Information
--

EASDeploymentChargingInformation	::= SET
{
	eASDeploymentRequirements			[0] EASDeploymentRequirements OPTIONAL,
	lCMStartTime						[1] TimeStamp,
	lCMEndTime							[2] TimeStamp,
	lCMEventType						[3]	ManagementOperation OPTIONAL,
	satelliteBackhaulInformation		[4] SatelliteBackhaulInformation OPTIONAL

}

--
-- Prose Charging Information--
--
-- See TS 32.277 [34] for more information
-- See clause 5.2.4.7 for ProSe CDR types definition


ProseChargingInformation		::= SET
{
	announcingPlmnID						[0] PLMN-Id OPTIONAL,
	announcingUeHplmnIdentifier				[1] PLMN-Id OPTIONAL,
	announcingUeVplmnIdentifier				[2] PLMN-Id OPTIONAL,
	monitoringUeHplmnIdentifier				[3] PLMN-Id OPTIONAL,
	monitoringUeVplmnIdentifier				[4] PLMN-Id OPTIONAL,
	discovererUeHplmnIdentifier				[5] PLMN-Id OPTIONAL,
	discovererUeVplmnIdentifier				[6] PLMN-Id OPTIONAL,
	discovereeUeHplmnIdentifier				[8] PLMN-Id OPTIONAL,
	discovereeUeVplmnIdentifier				[9] PLMN-Id OPTIONAL,
	monitoredPlmnIdentifier					[10] PLMN-Id OPTIONAL,
	proseApplicationID						[11] UTF8String OPTIONAL,
	applicationID							[12] UTF8String OPTIONAL,
	applicationSpecificDataList				[13] SEQUENCE OF AppSpecificData,
	proseFunctionality						[14] ProseFunctionality OPTIONAL,
	proseEventType							[15] ProSeEventType OPTIONAL,
	directDiscoveryModel					[16] UTF8String OPTIONAL,
	validityPeriod							[17] INTEGER OPTIONAL,
	roleOfUE								[18] ProSeUERole OPTIONAL,
	proseRequestTimestamp					[19] TimeStamp OPTIONAL,
	pC3ProtocolCause						[20] INTEGER OPTIONAL,
	monitoringUEIdentifier					[21] SubscriptionID OPTIONAL,
	requestedPLMNIdentifier					[22] PLMN-Id OPTIONAL,
	timeWindow								[23] INTEGER OPTIONAL,
	rangeClass								[24] RangeClass OPTIONAL,
	proximityAlertIndication				[25] ProximityAlertIndication OPTIONAL,
	proximityAlertTimestamp					[26] TimeStamp OPTIONAL,
	proximityCancellationTimestamp			[27] TimeStamp OPTIONAL,
	relayIPAddress							[28] IPAddress OPTIONAL,
	proseUEToNetworkRelayUEID				[29] OCTET STRING OPTIONAL,
	proseDestinationLayer2ID				[30] OCTET STRING OPTIONAL,
	pFIContainerInformation					[31] SEQUENCE OF PFIContainerInformation OPTIONAL,
	transmissionDataContainer				[32] SEQUENCE OF ChangeOfProSeCondition OPTIONAL,
	receptionDataContainer					[33] SEQUENCE OF ChangeOfProSeCondition OPTIONAL,
	hopCount					            [34] INTEGER OPTIONAL,
	intermediateRelayInformationContainer	[35] SEQUENCE OF IntermeidateRelayInformation OPTIONAL,
	proSeUEtoUERelayUEID					[36] UTF8String OPTIONAL,
	proSeUEtoUETargetEndUEIPAddress			[37] IPAddress OPTIONAL		


}

--
-- MMS Charging Information
--

MMSChargingInformation	::= SET
{
	mMOriginatorInfo			[1] MMOriginatorInfo OPTIONAL,
	mMRecipientInfoList		[2] SEQUENCE OF MMRecipientInfo OPTIONAL,
	userLocationInformation		[3] UserLocationInformation OPTIONAL,
	uETimeZone 					[4] MSTimeZone OPTIONAL,
	rATType						[5] RATType OPTIONAL,
	correlationInformation		[6] UTF8String OPTIONAL,
	submissionTime				[7] TimeStamp OPTIONAL,
	mMContentType				[8] MMContentType OPTIONAL,
	mMPriority					[9] PriorityType OPTIONAL,
	messageID					[10] UTF8String OPTIONAL,
	messageType					[11] UTF8String OPTIONAL,
	messageSize					[12] INTEGER OPTIONAL,
	messageClass				[13] UTF8String OPTIONAL,
	deliveryReportRequested		[14] BOOLEAN OPTIONAL,
	readReplyReportRequested	[15] BOOLEAN OPTIONAL,
	applicID					[16] UTF8String OPTIONAL,
	replyApplicID				[17] UTF8String OPTIONAL,
	auxApplicInfo				[18] UTF8String OPTIONAL,
	contentClass				[19] UTF8String OPTIONAL,
	dRMContent					[20] BOOLEAN OPTIONAL,
	adaptations					[21] BOOLEAN OPTIONAL,
	vasID						[22] UTF8String OPTIONAL,
	vaspID						[23] UTF8String OPTIONAL

}

--
-- NSACF Charging Information
--


NSACFChargingInformation 	::= SET
{
	nSACFChargingIndicator							[1] BOOLEAN OPTIONAL

}


--
-- TSN charging Information
-- See TS 32.282 [43] for more information
--

TSNChargingInformation	::= SET
{
	dNN										[0] DataNetworkNameIdentifier OPTIONAL,
	sNSSAI									[1] SingleNSSAI OPTIONAL,
	internalGroupIdentifier					[2] InternalGroupIdentifier OPTIONAL,
	externalIndividualIdList				[3] SEQUENCE OF InvolvedParty OPTIONAL,
	fiveGSBridgeInformation					[4] FiveGSBridgeInformation OPTIONAL,
	tSNQoSInformation						[5] TSNQoSInformation OPTIONAL,
	tSCAssistanceInformation				[6] TSCAssistanceInformation OPTIONAL,
	timeSynchronizationInformation			[7] TimeSynchronizationInformation OPTIONAL
}


--
-- MBS Session charging Information
--

MbsSessionChargingInformation ::= SET
{
	mBSSessionID 				[1] MbsSessionId,
	mBSServiceType				[2] MbsServiceType,
	serviceArea					[3] ServiceArea OPTIONAL,
	mBSStartTime 				[4] TimeStamp OPTIONAL,
	mBSStopTime					[5] TimeStamp OPTIONAL,
	servingNetworkFunctionID	[6] SEQUENCE OF ServingNetworkFunctionID OPTIONAL,
	mBSSessionActivityStatus	[7] MbsSessionActivityStatus

}


--
-- Inter-CHF Information
--
--
-- See TS 32.255 [15] and TS 32.256 [16] for more information
--


InterCHFInformation	::= SET
{
	remoteCHFResource		[0] UTF8String OPTIONAL,
	originalNFConsumerId	[1] NetworkFunctionInformation OPTIONAL
}


--
-- NSSAA Charging Information
--


NSSAAChargingInformation 	::= SET
{
	nSSAAMessageType				[0] NSSAAMessageType,
	userIdentification				[1] InvolvedParty OPTIONAL,
	aAAPAddress 					[2] NodeAddress OPTIONAL,
	aAASAddress 					[3] NodeAddress OPTIONAL,
	eAPIDResponse 					[4] EAPIDResponse OPTIONAL,
	eAPAuthStatus 					[5] EAPAuthStatus OPTIONAL,
	aMFIdentifier					[6] AMFID OPTIONAL

}


--
-- 5GS LCS Charging Information
--

RangingSLChargingInformation	::= SET
{
	targetUEID								[0] SubscriptionID OPTIONAL,
	sLReferenceUEID							[1] SubscriptionID OPTIONAL,
	sLPositioningServerUEID					[2] SubscriptionID OPTIONAL,
	locatedUEID								[3] SubscriptionID OPTIONAL,
	locationType							[4] LocationType OPTIONAL,
	locationEstimate						[5] UserLocationInformationStructured OPTIONAL
}

LCSInformation	::= SET
{
	lCSClientID								[0] LCSClientIdentity OPTIONAL,
	locationType							[1] LocationType OPTIONAL,
	locationEstimate						[2] UserLocationInformationStructured OPTIONAL,
	positioningData							[3] PositioningData OPTIONAL,
	targetUEID								[4] SubscriptionID OPTIONAL
}


--
-- CHF CHARGING TYPES
--

-- 
-- A
-- 


AFChargingID	::= UTF8String
--
-- See 3GPP TS 29.571 [249] for details.
-- 

AffinityAntiAffinity	::= SEQUENCE
{
	affinityEAS				[0] SEQUENCE OF UTF8String OPTIONAL,
	antiAffinityEAS			[1] SEQUENCE OF UTF8String OPTIONAL
}

AgeOfLocationInformation 	::= INTEGER


AdministrativeState 	::= ENUMERATED
{
	lOCKED		 (0),
	uNLOCKED 	 (1),
	sHUTTINGDOWN (2)

}

AccessType	::= ENUMERATED
{
	threeGPPAccess					(0),
	nonThreeGPPAccess				(1)

}


AllocatedUnit 	::= SEQUENCE
{
	quotaManagementIndicator			[0] BOOLEAN OPTIONAL,
	triggers							[1] SEQUENCE OF Trigger OPTIONAL,
	triggerTimeStamp					[2] TimeStamp OPTIONAL,
	localSequenceNumber					[3] LocalSequenceNumber OPTIONAL,
	nSACFContainerInformation			[4] NSACFContainerInformation OPTIONAL

}


AllocationRetentionPriority	::= SEQUENCE
{
	priorityLevel 			[1] INTEGER,
	preemptionCapability	[2] PreemptionCapability,
	preemptionVulnerability	[3] PreemptionVulnerability
}

 
AlternativeNSSAIMap		::= SEQUENCE
{
	snssai						[0] SingleNSSAI,
	alternativeSnssai			[1] SingleNSSAI
 
}


AMFID	::= OCTET STRING (SIZE(3..6))
-- See subclause 2.10.1 of 3GPP TS 23.003 [7] for encoding.
-- Any byte following the 3 first shall be set to ”F”

AmfUeNgapId	::= INTEGER

APIOperation	::= SEQUENCE
{
	name			[1] UTF8String,
	description		[2] UTF8String
}
APIResultCode	::= INTEGER
--
-- See specific API for more information
--
Area	::= SEQUENCE
{
	tacs 		[0] SEQUENCE OF TAC OPTIONAL,
	areaCode	[1] OCTET STRING OPTIONAL

}


ATSSSCapability	::= ENUMERATED
{
	aTSSS-LL					(0),
	mPTCP-ATSS-LL				(1),
	mPTCP-ATSS-LL-ASModeUL		(2),
	mPTCP-ATSS-LL-ExSDModeUL	(3), 
 	mPTCP-ATSS-LL-ASModeDLUL	(4) 

}


AuthorizedQoSInformation	::= SEQUENCE
--
-- See TS 32.291 [58] for more information
-- 
{
	fiveQi				[1] INTEGER OPTIONAL,
	aRP					[2] AllocationRetentionPriority OPTIONAL,
	priorityLevel 		[3] INTEGER OPTIONAL,
	averWindow			[4] INTEGER OPTIONAL,
	maxDataBurstVol		[5] INTEGER OPTIONAL
}
AvatarMedia	::= SEQUENCE
{
	resourceURL								[0] UTF8String OPTIONAL,
	mediaProcessingSpecification			[1] UTF8String OPTIONAL,
	avatarID					[2] UTF8String OPTIONAL
}
-- 
-- B
-- 

Bitrate	::= OCTET STRING
-- 
--  See 3GPP TS 29.571 [249] Bitrate data type.
-- 

-- 
-- C
-- 

CagId		::= OCTET STRING
-- 
-- See 3GPP TS 29.571 [249] for details
--


CellGlobalId	::= SEQUENCE
{
	plmnId              		[0] PLMN-Id,
	lac							[1] Lac,
	cellId					[2] CellId
}


CellId		::= UTF8String
-- 
-- See 3GPP TS 29.571 [249] for details
-- 


ChargingSessionIdentifier	::= OCTET STRING
-- See 3GPP TS 32.290 [57] for details.

ClockQuality					::= SEQUENCE
--
-- See 3GPP TS 29.571 [249] for details
-- 
{
	traceabilityToGnss						[1] BOOLEAN OPTIONAL,
	traceabilityToUtc						[2] BOOLEAN OPTIONAL,
	frequencyStability						[3] INTEGER OPTIONAL,
	clockAccuracy							[4] OCTET STRING (SIZE(2)) OPTIONAL
}


CoreNetworkType 		::= ENUMERATED
{
	fiveGC 		(0),
	ePC			(1)
}


-- 
-- D
-- 

DataNetworkNameIdentifier	::= IA5String (SIZE(1..63))
--
-- Network Identifier part of DNN in dot representation.
-- For example, if the complete DNN is 'apn1a.apn1b.apn1c.mnc022.mcc111.gprs'
-- The Identifier is 'apn1a.apn1b.apn1c' and is presented in this form in the CDR.
--


DelayToleranceIndicator   ::= ENUMERATED
{
	dTSupported 			(0),
	dTNotSupported			(1)
}

DNNSelectionMode	::= ENUMERATED
--
-- See Information Elements TS 29.502 [250] for more information
--
{
	uEorNetworkProvidedSubscriptionVerified				(0),
	uEProvidedSubscriptionNotVerified					(1),
	networkProvidedSubscriptionNotVerified				(2)
}

-- 
-- E
-- 


EAPAuthStatus		::= ENUMERATED
{
	eAPSuccess		(0),
	eAPFailure		(1),
	pending			(2)

}


EAPIDResponse		::= OCTET STRING 


-- 
-- See 3GPP TS 28.538 [256] for details
-- 

EASDeploymentRequirements	::= SEQUENCE
{
	requiredEASservingLocation			[0] ServingLocation OPTIONAL,
	softwareImageInfo					[1] SoftwareImageInfo OPTIONAL,
	affinityAntiAffinity				[2] AffinityAntiAffinity OPTIONAL,
	serviceContinuity					[3] BOOLEAN OPTIONAL,
	virtualResource						[4] VirtualResource OPTIONAL
}

-- 
-- See 3GPP TS 29.571 [249] for details
-- 

ENbId		::= UTF8String

-- 
-- See 3GPP TS 29.571 [249] for details
--
ExternalGroupIdentifier		::= UTF8String
-- 
-- See 3GPP TS 29.571 [249] for details
--

EstablishedConnectionInfo ::= SEQUENCE
{
	uPFIDs			[0] SEQUENCE OF NetworkFunctionName OPTIONAL,
	ranNodeIDs		[1] SEQUENCE OF GlobalRanNodeId OPTIONAL
}


EutraLocation	::= SEQUENCE
{
	tai							[0] TAI OPTIONAL,
	ecgi						[1] Ecgi OPTIONAL,
	ageOfLocationInformation		[3] AgeOfLocationInformation OPTIONAL,
	ueLocationTimestamp			[4] TimeStamp OPTIONAL,
	geographicalInformation		[5] GeographicalInformation	OPTIONAL,
	geodeticInformation			[6] GeodeticInformation OPTIONAL,
	globalNgenbId				[7] GlobalRanNodeId OPTIONAL,
	globalENbId					[8] GlobalRanNodeId OPTIONAL

}





EnhancedDiagnostics5G					::= SEQUENCE
{
	rANNASRelCause						[0] SEQUENCE OF RANNASRelCause
}



-- 
-- F
-- 
FiveGLANTypeService			::= SEQUENCE
{
	internalGroupIdentifier		[1] UTF8String
}


FiveGMMCapability	::= OCTET STRING
-- 
-- See 3GPP TS 29.571 [249] for details
-- 

FiveGMmCause	::= INTEGER
-- 
-- See 3GPP TS 29.571 [249] for details
-- 

FiveGMulticastService	::= SEQUENCE
{
	mBSSessionIDList		[0] SEQUENCE OF MbsSessionId
}


FiveGQoSInformation	::= SEQUENCE
--
-- See TS 32.291 [58] for more information
-- 
{
	fiveQi					[1] INTEGER OPTIONAL,
	aRP						[2] AllocationRetentionPriority OPTIONAL,
	qoSNotificationControl	[3] BOOLEAN OPTIONAL,
	reflectiveQos			[4] BOOLEAN OPTIONAL,
	maxbitrateUL				[5] Bitrate OPTIONAL,
	maxbitrateDL				[6] Bitrate OPTIONAL,
	guaranteedbitrateUL		[7] Bitrate OPTIONAL,
	guaranteedbitrateDL		[8] Bitrate OPTIONAL,
	priorityLevel 			[9] INTEGER OPTIONAL,
	averWindow				[10] INTEGER OPTIONAL,
	maxDataBurstVol			[11] INTEGER OPTIONAL,
	maxPacketLossRateDL 		[12] INTEGER OPTIONAL,
	maxPacketLossRateUL 		[13] INTEGER OPTIONAL
}

FiveGSBridgeInformation	::= SEQUENCE
{
	bridgeId							[1] INTEGER,
	nWTTPortNumber						[2] INTEGER OPTIONAL,
	dSTTPortNumber						[3] INTEGER OPTIONAL
}


FiveGSmCause	::= INTEGER
-- 
-- See 3GPP TS 29.571 [249] for details
-- 


-- 
-- G
-- 

GCI		::= UTF8String
-- 
-- See 3GPP TS 29.571 [249] for details
-- 


GeodeticInformation 	::= UTF8String
-- 
-- See 3GPP TS 29.571 [249] for details
-- 


GeographicalInformation ::= UTF8String
-- 
-- See 3GPP TS 29.571 [249] for details
-- 

GeographicalLocation ::= SEQUENCE
{	
	geographicalCoordinates			[0] GeographicalCoordinates OPTIONAL,
	civicLocation					[1] OCTET STRING OPTIONAL
}

GeographicalCoordinates::= SEQUENCE
{
	latitude			[0] INTEGER OPTIONAL,
	longitude			[1] INTEGER OPTIONAL
}

GeraLocation	::= SEQUENCE
{
	locationNumber              [0] LocationNumber OPTIONAL,
	cgi							[1] CellGlobalId OPTIONAL,
	sai						[2] ServiceAreaId OPTIONAL,
	lai							[3] LocationAreaId OPTIONAL,
	rai						[4] RoutingAreaId OPTIONAL,
	vlrNumber				[5] VlrNumber OPTIONAL,
	mscNumber				[6] MscNumber OPTIONAL,
	ageOfLocationInformation	[7] AgeOfLocationInformation OPTIONAL,
	ueLocationTimestamp			[8] TimeStamp OPTIONAL,
	geographicalInformation		[9] GeographicalInformation	OPTIONAL,
	geodeticInformation			[10] GeodeticInformation OPTIONAL
}


GLI		::= UTF8String
-- 
-- See 3GPP TS 29.571 [249] for details
-- 


GlobalRanNodeId		::= SEQUENCE 
{
	pLMNId		[0] PLMN-Id OPTIONAL,
	n3IwfId		[1] N3IwFId OPTIONAL,
	gNbId		[2] GNbId OPTIONAL,
	ngeNbId		[3] NgeNbId OPTIONAL,
	wagfId		[4] WAgfId OPTIONAL,
	tngfId		[5] TngfId OPTIONAL,
	nid			[6] Nid OPTIONAL,
	eNbId		[7] ENbId OPTIONAL

}
 

GNbId		::= SEQUENCE
{
	bitLength	[0] INTEGER,
	gNbValue	[1] IA5String (SIZE(6..8))

}

-- 
-- H
-- 
HFCNodeId		::= UTF8String
-- 
-- See 3GPP TS 29.571 [249] for details
--

-- 
-- I 
-- 

IMSDCAppInfo 	::= SET
{
	applicationId			[0] UTF8String OPTIONAL,
	httpUrl					[1] IMSDCUrlInfo OPTIONAL
}

IMSDCUrlInfo 	::= SET
{
	streamId				[0] INTEGER OPTIONAL,
	replaceHttpUrl			[1] UTF8String OPTIONAL
}

IMSNodeFunctionality	::= ENUMERATED
{
	iMS-GWF				(0),
	aS					(1),
	mRFC				(2),
	dCSF				(3)
}

IMSSessionInformation ::= SEQUENCE 
{
	callerInformation	[0] SEQUENCE OF InvolvedParty OPTIONAL,
	calleeInformation	[1] CalleePartyInformation OPTIONAL
}

IMSTrigger			::= INTEGER
{
--Initial
	sIPInvite									(1),
--Change of charging conditions
	sIPReInviteOrUpdate							(2),
	sIP2xxAcknowledging							(3),
	sIP1xxProvisionalResponse					(4),
	sIP4xx5xxOr6xxResponse						(5),
	otherSipMessage								(6),
--CHF Limit
	expiryOfTimeLimit							(7),
	expiryOfLimitOfNumOfChConditionChanges		(8),
--Quota management
	timeThresholdReached						(9),
	timeQuotaExhausted							(10),
	unitQuotaExhausted							(11),
	expiryOfQuotaValidityTime					(12),
	expiryOfQuotaHoldingTime					(13),
	reAuthorizationReqByChf						(14),
--Other
	managementIntervention						(15),
--Termination
	sIP2xxAcknowledgingASipBye					(16),
	abortingASipSessionSetup					(17),
	sIP3xxFinalOrRedirectionResponse			(18),
	sIP4xx5xxOr6xxFinalResponse					(19),
	sIPByeMessage								(20)
}


IncompleteCDRIndication	::= SEQUENCE
-- The values are TRUE if the corresponding message was lost, FALSE if it is not lost
-- and not included if the status is unknown
{
	initialLost		[0] BOOLEAN OPTIONAL,	-- Initial was lost
	updateLost		[1] BOOLEAN OPTIONAL,	-- An Update was lost, 
	terminationLost	[2] BOOLEAN OPTIONAL	-- Termination was lost
}

InternalGroupIdentifier		::= UTF8String
-- 
-- See 3GPP TS 29.571 [249] for details
-- 

IntermeidateRelayInformation	::= SEQUENCE
{
	intermediateRelayIPAddress				[0] IPAddress OPTIONAL,
	proSeUEtoNetworkIntermediateRelayUEID	[1] UTF8String OPTIONAL

}

-- 
-- K
-- 
KPIType 	::= ENUMERATED
{
	numOfBits 										(0),
	numOfBitsRANBased								(1),
	invOfLatency									(2),
	numOfBitsInvOfLatency							(3),
	maxRegSubs										(4),
	meanActiveUEs									(5)
}

-- 
-- L 
-- 
Lac		::= UTF8String
-- 
-- See 3GPP TS 29.571 [249] for details
-- 


LineType		::= ENUMERATED
{
	dSL 	(0),
	pON		(1)

}

LocationAreaId	::= SEQUENCE
{
	plmnId              		[0] PLMN-Id,
	lac							[1] Lac
}

LocationEstimate	::= SEQUENCE
{
	userLocationInformation					[1] UserLocationInformation OPTIONAL,
	horizontalAccuracy						[2] OCTET STRING OPTIONAL,
	verticalAccuracy						[3] OCTET STRING OPTIONAL
}

LocationNumber	::= UTF8String
-- 
-- See 3GPP TS 29.571 [249] for details
-- 

LocationReportingMessageType		::= INTEGER

LocationType			::= ENUMERATED
{
	currentLocation				(0),
	lastKnownLocation			(1),
	initialLocation				(2),
	deferredLocation			(3),
	notificationVerification	(4)
}


-- 
-- M
-- 

ManagementOperation 	::= ENUMERATED
{
	createMOI 			(0),
	modifyMOIAttributes	(1),
	deleteMOI			(2),
	notifyMOICreation	(3),
	notifyMOIAttrChange	(4),
	notifyMOIDeletion	(5)

}

ManagementOperationStatus 	::= ENUMERATED
{
	oPERATION-SUCCEEDED	(0),
	oPERATION-FAILED	(1)

}

MbsContainerInformation ::= SEQUENCE 
{
	timeOfFirstUsage			[0] TimeStamp OPTIONAL,
	timeOfLastUsage				[1] TimeStamp OPTIONAL,
	qoSInformation				[2] FiveGQoSInformation OPTIONAL,
	establishedConnectionInfo	[3] EstablishedConnectionInfo OPTIONAL
}

MBSMFTrigger	::= INTEGER
{
	startOfMBSSession							(1),
-- Change of Charging conditions
	connectionEstablishedWithNGRAN				(100),
	connectionReleasedWithNGRAN					(101),
	connectionEstablishedWithUPF				(102),
	tariffTimeChange							(103),
	connectionReleasedWithUPF					(104),
	mBSSessionContextUpdate						(105),
	mBSSessionActivityStatusChangetoActive		(106),
	mBSSessionActivityStatusChangetoInactive	(107),


-- Limit per MBS session
	mBSSessionExpiryDataTimeLimit				(200),
	mBSSessionExpiryDataVolumeLimit				(201),
	mBSSessionExpiryChargingConditionChanges	(202),
-- Quota management
	timeThresholdReached						(400),
	timeQuotaExhausted							(401),
-- Others 
	endOfMBSSession								(500)
}

MbsServiceArea ::= SEQUENCE
-- 
-- See 3GPP TS 29.571 [249] for details
-- 
{
	ncgiList	[0] SEQUENCE OF NcgiTai OPTIONAL,
	taiList		[1] SEQUENCE OF TAI OPTIONAL

}

MbsServiceType ::= ENUMERATED
-- 
-- See 3GPP TS 29.571 [249] for details
-- 
{
	multicast (0),
	broadcast (1)
}


MbsSessionActivityStatus ::= ENUMERATED
-- 
-- See 3GPP TS 29.571 [249] for details
-- 
{
	active 			(0),
	inactive		(1)
}
MbsSessionId	::= SEQUENCE
-- See 3GPP TS 29.571 [249] for details.
{
	tMGI			[0] TMGI OPTIONAL,
	ssm				[1] Ssm OPTIONAL,
	nid				[2] Nid OPTIONAL
}

MbsDeliveryMethod	::= ENUMERATED
{
	shared 			(0),
	individual		(1)
}


MnSConsumerIdentifier		::= OCTET STRING 


MAPDUSessionIndicator	::= ENUMERATED
{
	mAPDURequest 					(0),
	mAPDUNetworkUpgradeAllowed		(1)

}


MAPDUSessionInformation	::= SEQUENCE
{
	mAPDUSessionIndicator			[0] MAPDUSessionIndicator OPTIONAL,
	aTSSSCapability					[1] ATSSSCapability OPTIONAL

}



MAPDUSteeringFunctionality	::= ENUMERATED
{
	mPTCP 		(0),
	aTSSSLL		(1)

}


MAPDUSteeringMode	::= SEQUENCE
{
	steerModeValue			[0] SteerModeValue OPTIONAL,
	active					[1] AccessType OPTIONAL,
	standby					[2] AccessType OPTIONAL,
	threegLoad				[3] INTEGER OPTIONAL,
	prioAcc					[4] AccessType OPTIONAL

}
MediaResource	::= SEQUENCE
{
	mediaID						[0] UTF8String,
	mediaResourceCapability		[1] MediaResourceType,
	avatarMedia					[2] AvatarMedia OPTIONAL
}

MediaResourceType 		::= ENUMERATED
{
	dc 			(0),
	audio		(1),
	video		(2)
}

MICOModeIndication 		::= ENUMERATED
{
	mICOMode 			(0),
	noMICOMode			(1)
}

MMAddContentInfo	::= SEQUENCE 
{
	typeNumber			[0] UTF8String OPTIONAL,
	addtypeInfo			[1] UTF8String OPTIONAL,
	contentSize			[2] INTEGER OPTIONAL
}

MMContentType	::= SEQUENCE 
{
	typeNumber			[0] UTF8String OPTIONAL,
	addtypeInfo			[1] UTF8String OPTIONAL,
	contentSize			[2] INTEGER OPTIONAL,
	mmAddContentInfo	[3] SEQUENCE OF MMAddContentInfo OPTIONAL
}

MMOriginatorInfo	::= SEQUENCE 
{
	originatorIMSI				[0] IMSI OPTIONAL,
	originatorMSISDN			[1] MSISDN OPTIONAL,
	originatorOtherAddresses	[2] SEQUENCE OF SMAddressInfo OPTIONAL
}

MMRecipientInfo	::= SEQUENCE 
{
	recipientIMSI				[0] IMSI OPTIONAL,
	recipientMSISDN				[1] MSISDN OPTIONAL,
	recipientOtherAddresses		[2] SEQUENCE OF SMAddressInfo OPTIONAL
}

MobilityLevel	::= ENUMERATED
{
	stationary			(0),
	nomadic				(1),
	restrictedMobility	(2),
	fullyMobility		(3)

}
 

MscNumber	::= UTF8String
-- 
-- See 3GPP TS 29.571 [249] for details
-- 


MultipleUnitUsage 		::= SEQUENCE
{
	ratingGroup							[0] RatingGroupId,
	usedUnitContainers					[1] SEQUENCE OF UsedUnitContainer OPTIONAL,
	uPFID								[2] NetworkFunctionName OPTIONAL,
	multihomedPDUAddress				[3] PDUAddress OPTIONAL,
	allocatedUnit			 			[4] AllocatedUnit OPTIONAL,
	mBUPFID								[5] NetworkFunctionName OPTIONAL
}

MultipleQFIContainer 		::= SEQUENCE
{
	qosFlowId								[0] QoSFlowId OPTIONAL,
	triggers								[1] SEQUENCE OF Trigger OPTIONAL,
	triggerTimeStamp						[2] TimeStamp OPTIONAL,
	dataTotalVolume							[3] DataVolumeOctets OPTIONAL,
	dataVolumeUplink						[4] DataVolumeOctets OPTIONAL,
	dataVolumeDownlink						[5] DataVolumeOctets OPTIONAL,
	localSequenceNumber						[6] LocalSequenceNumber OPTIONAL,
	timeOfFirstUsage						[8] TimeStamp OPTIONAL,
	timeOfLastUsage							[9] TimeStamp OPTIONAL,
	qoSInformation							[10] FiveGQoSInformation OPTIONAL,
	userLocationInformation					[11] UserLocationInformation OPTIONAL,
	uETimeZone	 							[12] MSTimeZone OPTIONAL,
	presenceReportingAreaInfo				[13] PresenceReportingAreaInfo OPTIONAL,
	rATType									[14] RATType OPTIONAL,
	reportTime								[15] TimeStamp,
	servingNetworkFunctionID				[16] SEQUENCE OF ServingNetworkFunctionID OPTIONAL,
	threeGPPPSDataOffStatus					[17] ThreeGPPPSDataOffStatus OPTIONAL,
	threeGPPChargingID						[18] ChargingID OPTIONAL,
	diagnostics						[19] Diagnostics OPTIONAL,
	extensionDiagnostics					[20] EnhancedDiagnostics OPTIONAL,
	qoSCharacteristics						[21] QoSCharacteristics OPTIONAL,
	time									[22] CallDuration OPTIONAL,
	userLocationInformationASN1				[23] UserLocationInformationStructured OPTIONAL,
	listOfPresenceReportingAreaInformation	[39] SEQUENCE OF PresenceReportingAreaInfo OPTIONAL
}

-- 
-- N
-- 
N2ConnectionMessageType		::= INTEGER

N3IwFId		::= IA5String (SIZE(1..16))
--
-- See 3GPP TS 29.571 [249] for details.
-- 

N3gaLocation	::= SEQUENCE
{
	n3gppTai			[0] TAI OPTIONAL,
	n3IwfId			[1] N3IwFId OPTIONAL,
	ueIpv4Addr		[2] IPAddress OPTIONAL,
	ueIpv6Addr		[3] IPAddress OPTIONAL,
	portNumber		[4] INTEGER	OPTIONAL, 
	tnapId			[5] TNAPId	OPTIONAL, 
	twapId			[6] TWAPId	OPTIONAL,
 	hfcNodeId		[7] HFCNodeId OPTIONAL,
	w5gbanLineType	[8] LineType OPTIONAL,
	gli				[9] GLI OPTIONAL,
	gci				[10] GCI OPTIONAL

}

NcgiTai ::= SEQUENCE
-- 
-- See 3GPP TS 29.571 [249] for details
-- 
{
	tai 		[0] TAI,
	cellList 	[1] SEQUENCE OF Ncgi
}

NetworkSharingContainerInformation		::= SEQUENCE
{
	uplinkVolume					[0] INTEGER OPTIONAL,
	downlinkVolume					[1] INTEGER OPTIONAL,
	numberOfPDUSessionsReq			[2] INTEGER OPTIONAL,
	numberOfPDUSessionsSuccess		[3] INTEGER OPTIONAL
}

NetworkSliceEE 		::= SEQUENCE
{
	networkSliceType			[1] NetworkSliceType OPTIONAL,
	kpiType						[2] KPIType OPTIONAL,
	performance					[3] REAL OPTIONAL
}

NetworkSliceType 	::= ENUMERATED
{
	eMBB 			(0),
	uRLLC			(1),
	mIoT			(2)
}

NSACFContainerInformation 		::= SEQUENCE
{
	numberOfUEs 					[0] INTEGER OPTIONAL,
	numberOfPDUs					[1] INTEGER OPTIONAL

}

NSACFTrigger			::= INTEGER
{
--Initial
	nSACThresholdInitial						(1),
--Change of charging conditions
	nSACThresholdUpwardsReached					(2),
	nSACThresholdUpwardsCrossed					(3),
	nSACThresholdDownwardsCrossed				(4),
--Quota management
	nSACQuotaThreshold							(5),
	nSACQuotaExhausted							(6),
	nSACValidityTime							(7),
	nSACQHT										(8),
	nSACThresholdTermination					(9),
--Termination
	nSTermination								(10)
}

NSSAAMessageType		::= ENUMERATED
{
	authenticate					(0),
	reAuthenticationNotification	(1),
	revocationNotification			(2)

}
 

NrLocation	::= SEQUENCE
{
	tai							[0] TAI OPTIONAL,
	ncgi						[1] Ncgi OPTIONAL,
	ageOfLocationInformation		[2] AgeOfLocationInformation OPTIONAL,
	ueLocationTimestamp			[3] TimeStamp OPTIONAL,
	geographicalInformation		[4] GeographicalInformation	OPTIONAL,
	geodeticInformation			[5] GeodeticInformation OPTIONAL,
	globalGnbId					[6] GlobalRanNodeId OPTIONAL,
	ntnTaiInfo					[7] NtnTaiInfo OPTIONAL

}


-- 
-- See 3GPP TS 29.571 [249] for details
-- 


NetworkAreaInfo	::= SEQUENCE
{
	ecgis				[0] SEQUENCE OF Ecgi OPTIONAL,
	ncgis				[1] SEQUENCE OF Ncgi OPTIONAL,
	gRanNodeIds			[2] SEQUENCE OF GlobalRanNodeId OPTIONAL,
	tais				[3] SEQUENCE OF TAI OPTIONAL
}


NetworkFunctionInformation	::= SEQUENCE
{
	networkFunctionality					[0] NetworkFunctionality,
	networkFunctionName					[1] NetworkFunctionName OPTIONAL,
	networkFunctionIPv4Address			[2] IPAddress OPTIONAL,
	networkFunctionPLMNIdentifier		[3] PLMN-Id OPTIONAL,
	networkFunctionIPv6Address			[4] IPAddress OPTIONAL,
	networkFunctionFQDN					[5] NodeAddress OPTIONAL

}

NetworkFunctionName	::= IA5String (SIZE(1..36))
-- Shall be a Universally Unique Identifier (UUID) version 4, as described in IETF RFC 4122 [410]

NetworkFunctionality	::= ENUMERATED
{
	cHF				(0),
	-- CHF is applicable in two scenarios: inter-CHF communication andfailure cases
	sMF				(1),
-- SMF is applicable in two scenarios: as NF consumer of CHF services, and as API Target NF 
-- in NEF charging
	aMF				(2),
-- AMF is applicable in two scenario: as NF consumer of CHF services, and as API Target NF
-- in NEF charging
	sMSF			(3),
	sGW				(4),
	-- SGW is only applicable for interworking with EPC scenario
	-- when UE is connected to P-GW+SMF via EPC
	iSMF			(5),
	ePDG			(6),
	-- ePDG is only applicable for interworking with EPC scenario
	-- when UE is connected to P-GW+SMF via EPC/ePDG
	cEF				(7),
	nEF			(8),
	pGWCSMF			(9),
	mnS-Producer 	(10),
	sGSN			(11),
	-- SGSN is only applicable when UE is connected to SMF+PGW-C via GERAN/UTRAN
	fiveGDDNMF		(12),
	vSMF			(13),
	-- vSMF may be used instead of sMF in roaming scenarios}
	iMS-Node		(14),
	eES				(15),
	mMS-Node		(16),
	pCF				(17),
	-- PCF is applicable only as API Target NF in NEF charging
	uDM				(18),
	-- UDM is applicable only as API Target NF in NEF charging
	uPF				(19),
	-- UPF is applicable only as API Target NF in NEF charging
	tSN-AF			(20),
	tSNTSF			(21),
	mB-SMF			(22),
	aIOTF			(23)
	-- AIOTF is applicable only as API Target NF in NEF charging
	nWDAF			(24)
}

NgApCause	::= SEQUENCE
-- See 3GPP TS 29.571 [249] for details.
{
	group			[0] INTEGER,
	value			[1] INTEGER
}

NgeNbId		::= IA5String (SIZE(1..21))
--
-- See 3GPP TS 29.571 [249] for details.
-- 

NGRANSecondaryRATType	::= OCTET STRING
-- 
-- "NR" or "EUTRA"
-- 
 

NGRANSecondaryRATUsageReport	::= SEQUENCE
{
	nGRANSecondaryRATType			[0] NGRANSecondaryRATType OPTIONAL,
	qosFlowsUsageReports			[1] SEQUENCE OF QosFlowsUsageReport OPTIONAL
}




NsiLoadLevelInfo		::= SEQUENCE
-- 
-- See 3GPP TS 29.520 [233] for details
-- 
{
	loadLevelInformation				[0] INTEGER OPTIONAL,
	snssai								[1] SingleNSSAI OPTIONAL,
	nsiId								[2] OCTET STRING OPTIONAL
}

NSPAContainerInformation		::= SEQUENCE
{
--	latency								[0] INTEGER OPTIONAL,
--	throughput							[1] Throughput OPTIONAL,
--	maximumPacketLossRate				[3] UTF8String OPTIONAL,
	serviceExperienceStatisticsData		[4] ServiceExperienceInfo OPTIONAL,
	numberOfPDUSessions					[5] INTEGER OPTIONAL,
	numberOfRegisteredSubscribers		[6] INTEGER OPTIONAL,
	loadLevel							[7] NsiLoadLevelInfo OPTIONAL,
	uplinkLatency						[8] INTEGER OPTIONAL,
	downlinkLatency						[9] INTEGER OPTIONAL,
	uplinkThroughput						[10] Throughput OPTIONAL,
	downlinkThroughput					[11] Throughput OPTIONAL,
	maximumPacketLossRateUL				[12] INTEGER OPTIONAL,
	maximumPacketLossRateDL				[13] INTEGER OPTIONAL,
	estimatedEnergyConsumption			[14] INTEGER OPTIONAL,
	sourceNFIdentification				[15] NetworkFunctionInformation OPTIONAL
}

NSSAIMap		::= SEQUENCE
{
	servingSnssai						[0] SingleNSSAI,
	homeSnssai							[1] SingleNSSAI
 
}


NtnTaiInfo	::= SEQUENCE
{
	pLMNId			[0] PlmnIdNid,			
	tacList			[1] SEQUENCE OF TAC,
	derivedTac		[2]	TAC OPTIONAL
}


-- 
-- O
-- 


OperationalState 	::= ENUMERATED
{
	eNABLED	(0),
	dISABLED(1)

}


-- 
-- P
-- 


PartialRecordMethod	::= ENUMERATED
{
	default			(0),
	individual		(1)
}

PDUAddress 	::= SEQUENCE
{
	pDUIPv4Address				[0] IPAddress OPTIONAL,
	pDUIPv6AddresswithPrefix		[1] IPAddress OPTIONAL,
	iPV4dynamicAddressFlag		[2] DynamicAddressFlag OPTIONAL,
	iPV6dynamicPrefixFlag		[3] DynamicAddressFlag OPTIONAL,  
	additionalPDUIPv6Prefixes	[4]	SEQUENCE OF IPAddress OPTIONAL
}

PDUContainerInformation 		::= SEQUENCE
{
	chargingRuleBaseName					[0] ChargingRuleBaseName OPTIONAL,
	-- aFCorrelationInformation [1] is replaced by afChargingIdentifier [14]
	timeOfFirstUsage						[2] TimeStamp OPTIONAL,
	timeOfLastUsage							[3] TimeStamp OPTIONAL,
	qoSInformation							[4] FiveGQoSInformation OPTIONAL,
	userLocationInformation					[5] UserLocationInformation OPTIONAL,
	presenceReportingAreaInfo				[6] PresenceReportingAreaInfo OPTIONAL,
	rATType									[7] RATType OPTIONAL,
	sponsorIdentity							[8] OCTET STRING OPTIONAL,
	applicationServiceProviderIdentity		[9] OCTET STRING OPTIONAL,
	servingNetworkFunctionID				[10] SEQUENCE OF ServingNetworkFunctionID OPTIONAL,
	uETimeZone 								[11] MSTimeZone OPTIONAL,
	threeGPPPSDataOffStatus					[12] ThreeGPPPSDataOffStatus OPTIONAL,
	qoSCharacteristics						[13] QoSCharacteristics OPTIONAL,
	afChargingIdentifier					[14] ChargingID OPTIONAL,
	afChargingIdString						[15] AFChargingID OPTIONAL,
	mAPDUSteeringFunctionality				[16] MAPDUSteeringFunctionality OPTIONAL,
	mAPDUSteeringMode						[17] MAPDUSteeringMode OPTIONAL,
	userLocationInformationASN1				[18] UserLocationInformationStructured OPTIONAL,
	listOfPresenceReportingAreaInformation	[19] SEQUENCE OF PresenceReportingAreaInfo OPTIONAL,
	trafficForwardingWay					[20] TrafficForwardingWay OPTIONAL,
	qosMonitoringReport						[21] QosMonitoringReport OPTIONAL,
	mBSSessionID							[22] MbsSessionId OPTIONAL,
	mBSDeliveryMethod						[23] MbsDeliveryMethod OPTIONAL
}

PDUSessionPairID	::= INTEGER

PDUSessionId 		::= INTEGER (0..255)
-- 
-- See 3GPP TS 29.571 [249] for details
-- 

PDUSessionType		::= ENUMERATED
{
	iPv4v6			(0),
	iPv4			(1),
	iPv6			(2),
	unstructured	(3),
	ethernet		(4)
}
-- See 3GPP TS 29.571 [249] for details.

PFIContainerInformation 		::= SEQUENCE
{
	pC5qosFlowId							[0] QoSFlowId OPTIONAL,
	timeOfFirstUsage						[1] TimeStamp OPTIONAL,
	timeOfLastUsage							[2] TimeStamp OPTIONAL,
	qoSInformation							[3] FiveGQoSInformation OPTIONAL,
	userLocationInformation					[4] UserLocationInformation OPTIONAL,
	uETimeZone	 							[5] MSTimeZone OPTIONAL,
	presenceReportingAreaInfo				[6] PresenceReportingAreaInfo OPTIONAL,
	reportTime								[7] TimeStamp,
	qoSCharacteristics						[8] QoSCharacteristics OPTIONAL
}

PlmnIdNid	::= SEQUENCE
{
	pLMNId		[0] PLMN-Id OPTIONAL,
	nid			[1] Nid OPTIONAL	
}
PreemptionCapability		::= ENUMERATED
{
	nOT-PREEMPT			(0),
	mAY-PREEMPT			(1)
}

PreemptionVulnerability		::= ENUMERATED
{
	nOT-PREEMPTABLE		(0),
	pREEMPTABLE			(1)
}


PC5ContainerInformation		::= SET
{
	coverageInfoList				[0] SEQUENCE OF CoverageInfo OPTIONAL,
	radioParameterSetInfoList		[1] SEQUENCE OF RadioParameterSetInfo OPTIONAL,
	transmitterInfoList				[2] SEQUENCE OF TransmitterInfo OPTIONAL,
	timeOfFirstTransmission			[3] TimeStamp OPTIONAL,
	timeOfFirstReception			[4] TimeStamp OPTIONAL
}
-- 
-- Q
-- 

QoSCharacteristics	::= OCTET STRING
-- 
-- This data is converted from JSON format of the QoSCharacteristics as described in TS 29.512
-- [251].
--

QoSFlowId		::= INTEGER

QosFlowsUsageReport		::= SEQUENCE
{
	qosFlowId						[0] QoSFlowId OPTIONAL,
	startTime						[1] TimeStamp,
	endTime							[2] TimeStamp,
	dataVolumeDownlink				[3] DataVolumeOctets,
	dataVolumeUplink					[4] DataVolumeOctets
}
QuotaManagementIndicator	::= ENUMERATED
{
	onlineCharging				(0),
	offlineCharging				(1),
	quotaManagementSuspended	(2)
}


QosMonitoringReport		::= SEQUENCE-- The maximum number of elements in the SEQUENCE of ulDelays,dlDelays and rtDelays is 2.
{
	ulDelays						 [0] SEQUENCE OF INTEGER OPTIONAL,
	dlDelays						 [1] SEQUENCE OF INTEGER OPTIONAL,
	rtDelays						 [2] SEQUENCE OF INTEGER OPTIONAL

}
-- 
-- R
-- 

Rac		::= UTF8String
-- 
-- See 3GPP TS 29.571 [249] for details
-- 


RanUeNgapId	::= INTEGER 


RANNASRelCause 		::= SEQUENCE
-- Mode details are described in TS 29.512[251].
{
	ngApCause		[0] NgApCause OPTIONAL,
	fivegMmCause	[1] FiveGMmCause OPTIONAL,
	fivegSmCause	[2] FiveGSmCause OPTIONAL,
	epsCause		[3] RANNASCause OPTIONAL
}

RatingIndicator	::= BOOLEAN
-- Included if the units have been rated.

RATType		::= INTEGER
--
-- This integer is based on the RatType specified in TS 29.571 [249]
-- with 3GPP RAT Type specified in TS 29.061 [216] added for backwards compatibility.
--
{
-- 0 reserved
	uTRAN			(1),
	gERAN			(2),
	wLAN			(3),
-- 4 reserved for GAN
-- 5 reserved for HSPA Evolution
	eUTRAN			(6),
	virtual			(7),
-- 8 reserved for nBIoT
-- 9 reserved for lTEM
	nR				(51),
	nR-U			(52),
	eUTRAN-U		(53),
	lte-m			(54),
	wIRELINE		(55),
	wIRELINE-CABLE	(56),
	wIRELINE-BBF	(57),
	nR-REDCAP	(58),
	nR-LEO			(59),
	nR-MEO			(60),
	nR-GEO			(61),
	nR-OTHERSAT		(62),
	tRUSTED-N3GA	(65),
	tRUSTED-WLAN	(66)
-- 101 reserved for IEEE 802.16e
-- 102 reserved for 3GPP2 eHRPD
-- 103 reserved for 3GPP2 HRPD
-- 104 reserved for 3GPP2 1xRTT
-- 105 reserved for 3GPP2 UMB
}

RegistrationMessageType		::= ENUMERATED
{
	initial			(0),
	mobility		(1),
	periodic		(2),
	emergency		(3),
	deregistration	(4)
}

RestrictionType		::= ENUMERATED
{
	allowedAreas	(0),
	notAllowedAreas	(1)
}


RoamingChargingProfile 		::= SEQUENCE
{
	roamingTriggers			[0] SEQUENCE OF RoamingTrigger OPTIONAL,
	partialRecordMethod		[1] PartialRecordMethod OPTIONAL
}

RoamerInOut	::= ENUMERATED
{
	roamerInBound		(0),
	roamerOutBound		(1)
}

RoamingTrigger 		::= SEQUENCE
{
	trigger					[0] SMFTrigger OPTIONAL,
	triggerCategory			[1] TriggerCategory	 OPTIONAL,
	timeLimit				[2] CallDuration OPTIONAL,
	volumeLimit				[3] DataVolumeOctets OPTIONAL,
	maxNbChargingConditions	[4] INTEGER OPTIONAL
}

RoutingAreaId	::= SEQUENCE
{
	plmnId              		[0] PLMN-Id,
	lac							[1] Lac,
	rac					[2] Rac
}


RrcEstablishmentCause	::= OCTET STRING

RedundantTransmissionType		::= ENUMERATED
{
	nonTransmission				 (0),
	endToEndUserPlanePaths     	 (1),
	n3N9    		(2),
	transportLayer     	 			(3)
}


-- 
-- S
-- 

Sac		::= UTF8String
-- 
-- See 3GPP TS 29.571 [249] for details
-- 


SatelliteBackhaulInformation 	::= SEQUENCE
{
	satelliteBackhaulCategory			[0] SatelliteBackhaulCategory OPTIONAL,
	gEOSatelliteID					[1] UTF8String OPTIONAL 

}
-- See 3GPP TS 29.571 [249] for details.

SatelliteBackhaulCategory ::= ENUMERATED
{
	gEO   				(0),
	mEO 				(1),
	lEO					(2),
	oTHERSAT 			(3),
	dYNAMICGEO 			(4),
	dYNAMICMEO			(5),
	dYNAMICLEO 			(6),
	dYNAMICOTHERSAT 	(7),
	nONSATELLITE		(8)

}

SatelliteID 	::= UTF8String

ServiceArea ::= SEQUENCE
{
	mBSServiceArea	[0] MbsServiceArea OPTIONAL,
	uPFIDs			[1] SEQUENCE OF NetworkFunctionName OPTIONAL,
	ranNodeIDs		[2] SEQUENCE OF GlobalRanNodeId OPTIONAL
}

ServiceAreaId	::= SEQUENCE
{
	plmnId              		[0] PLMN-Id,
	lac							[1] Lac,
	sac					[2] Sac
}


ServiceAreaRestriction	::= SEQUENCE
{
	restrictionType					[0] RestrictionType OPTIONAL,
	areas							[1] SEQUENCE OF Area OPTIONAL,
	maxNumOfTAs						[2] INTEGER OPTIONAL,
	maxNumOfTAsForNotAllowedAreas	[3] INTEGER OPTIONAL

}
-- See 3GPP TS 29.571 [249] for details.

ServiceExperienceInfo	::= SEQUENCE
-- 
-- See 3GPP TS 29.520 [233] for details
-- 
{
	svcExprc						[0] SvcExperience OPTIONAL,
	svcExprcVariance				[1] INTEGER OPTIONAL,
	snssai						[2] SingleNSSAI OPTIONAL,
	appId						[3] OCTET STRING OPTIONAL,
	confidence					[4] INTEGER OPTIONAL,
	dnn							[5] DataNetworkNameIdentifier OPTIONAL,
	networkArea					[6] NetworkAreaInfo OPTIONAL,
	nsiId						[7] OCTET STRING OPTIONAL,
	ratio						[8] INTEGER OPTIONAL
}

ServiceProfileChargingInformation 	::= SET
{
--
-- attributes of the service profile: see TS 28.541 [254]
--
	serviceProfileIdentifier				[0] OCTET STRING OPTIONAL,
	sNSSAIList							[1] SEQUENCE OF SingleNSSAI OPTIONAL,
	sST			 						[2] SliceServiceType OPTIONAL,
	latency								[3] INTEGER OPTIONAL,
	availability							[4]	INTEGER OPTIONAL,
	resourceSharingLevel					[5] SharingLevel OPTIONAL,
	jitter								[6]	INTEGER OPTIONAL,
	reliability							[7] OCTET STRING OPTIONAL,
	maxNumberofUEs 						[8] INTEGER OPTIONAL,
	coverageArea 						[9] OCTET STRING OPTIONAL,
	uEMobilityLevel						[10] MobilityLevel OPTIONAL,
	delayToleranceIndicator 				[11] DelayToleranceIndicator OPTIONAL,
	dLThroughtputPerSlice				[12] Throughput OPTIONAL,
	dLThroughtputPerUE					[13] Throughput OPTIONAL,
	uLThroughtputPerSlice				[14] Throughput OPTIONAL,
	uLThroughtputPerUE					[15] Throughput OPTIONAL,
	maxNumberofPDUsessions 				[16] INTEGER OPTIONAL,
	kPIsMonitoringList 					[17] OCTET STRING OPTIONAL,
	supportedAccessTechnology			[18] INTEGER OPTIONAL,
	v2XCommunicationMode 				[19] V2XCommunicationModeIndicator OPTIONAL,
	energyEfficiency					[20] NetworkSliceEE	OPTIONAL,
	addServiceProfileChargingInfo		[100] OCTET STRING OPTIONAL

}

ServingLocation	::= SEQUENCE
{
	geographicalLocation				[0] SEQUENCE OF GeographicalLocation OPTIONAL,
	topologicalLocation					[1] TopologicalLocation OPTIONAL
}

ServingNetworkFunctionID	::= SEQUENCE
{
	servingNetworkFunctionInformation	[0] NetworkFunctionInformation,
	aMFIdentifier						[1] AMFID OPTIONAL

}

SessionAMBR	::= SEQUENCE
{
	ambrUL				[1] Bitrate,
	ambrDL				[2] Bitrate
}

SharingLevel	::= ENUMERATED
{
	sHARED			(0),
	nON-SHARED		(1)

}

SIPEventType	::= SEQUENCE
{
	sIPMethod              		[0] SIP-Method OPTIONAL,
	eventHeader					[1] INTEGER OPTIONAL,
	expiresHeader			[2] UTF8String OPTIONAL
}

SingleNSSAI	::= SEQUENCE
-- See S-NSSAI subclause 28.4.2 of TS 23.003 [200] for encoding.
{
	sST			[0] SliceServiceType,
	sD 			[1] SliceDifferentiator OPTIONAL
}

SliceServiceType ::= INTEGER (0..255)
--
-- See subclause 28.4.2 TS 23.003 [200]
--

SliceDifferentiator		::= OCTET STRING (SIZE(3))
--
-- See subclause 28.4.2 TS 23.003 [200]
--


SMdeliveryReportRequested ::= ENUMERATED
{
	yes		(0),
	no		(1)
}

SMFTrigger				::= INTEGER
{
	startOfPDUSession							(1),
	startOfServiceDataFlowNoSession				(2),
-- Change of Charging conditions
	qoSChange									(100),
	userLocationChange							(101),
	servingNodeChange							(102),
	presenceReportingAreaChange					(103),
	threeGPPPSDataOffStatusChange				(104),
	tariffTimeChange							(105),
	uETimeZoneChange							(106),
	pLMNChange									(107),
	rATTypeChange								(108),
	sessionAMBRChange							(109),
	additionOfUPF								(110),
	removalOfUPF 								(111),
	insertionOfISMF								(112),
	removalOfISMF								(113),
	changeOfISMF								(114),
	gFBRGuaranteedStatusChange					(115),
	additionOfAccess							(116),
	removalOfAccess 							(117),
	redundantTransmissionChange					(118),
	vSMFChange									(119),
	sNSSAIReplacement							(120),
	joinMulticastMBSSession						(121),
	mBSDeliveryMethodChange						(122),
	leaveMulticastMBSSession					(123),
	satelliteBackhaulCategoryChange				(124),
	satelliteBackhaulQoSChange					(125),
	gEOSatelliteIDCchange						(126),
-- Limit per PDU session
	pDUSessionExpiryDataTimeLimit				(200),
	pDUSessionExpiryDataVolumeLimit				(201),
	pDUSessionExpiryDataEventLimit				(202),
	pDUSessionExpiryChargingConditionChanges	(203),
-- Limit per Rating group
	ratingGroupDataTimeLimit					(300),
	ratingGroupDataVolumeLimit					(301),
	ratingGroupDataEventLimit					(302),
-- Quota management
	timeThresholdReached						(400),
	volumeThresholdReached						(401),
	unitThresholdReached						(402),
	timeQuotaExhausted							(403),
	volumeQuotaExhausted						(404),
	unitQuotaExhausted							(405),
	expiryOfQuotaValidityTime					(406),
	reAuthorizationRequest						(407),
	startOfServiceDataFlowNoValidQuota			(408),
	otherQuotaType								(409),
	expiryOfQuotaHoldingTime					(410),
	startOfSDFAdditionalAccessNoValidQuota		(411),
-- Others 
	terminationOfServiceDataFlow				(500),
	managementIntervention						(501),
	unitCountInactivityTime						(502),
	endOfPDUSession								(503),
	cHFResponseWithSessionTermination			(504),
	cHFAbortRequest								(505),
	abnormalRelease								(506),
	notProvidedBySMF							(507), -- used if not provided by SMF
-- Limit per QoS Flow
	qoSFlowExpiryDataTimeLimit					(600),
	qoSFlowExpiryDataVolumeLimit				(601),
-- interworking with EPC
	eCGIChange									(700),
	tAIChange									(701),
	handoverCancel								(702),
	handoverStart								(703),
	handoverComplete							(704),
-- GERAN/UTRAN access
	cGI-SAIChange								(705),
	rAIChange									(706)
}
-- See TS 32.255 [15] for details.

SMReplyPathRequested	::= ENUMERATED
{
	noReplyPathSet 			(0),
	replyPathSet			(1)
}

SMServiceType 	::= INTEGER
{
-- 0 to 10 VAS4SMS Short Message, see TS 22.142 [105] for details
	contentProcessing					(0),
	forwarding							(1),
	forwardingMultipleSubscriptions		(2),
	filtering 							(3),
	receipt								(4),
	networkStorage						(5),
	toMultipleDestinations				(6),
	virtualPrivateNetwork				(7),
	autoreply							(8),
	personalSignature					(9),
	deferredDelivery					(10)
-- 11 to 99	Reserved for 3GPP defined SM services
-- 100 to 199 Vendor specific SM services
}

SmsIndication   ::= ENUMERATED
{
	sMSSupported 			(0),
	sMSNotSupported			(1)
}

SNPNInformation   ::= SET
{
	sNPNID				[0] PlmnIdNid,
	accessType			[1] AccessType OPTIONAL, 
	n3IWFFQDN			[2] NodeAddress OPTIONAL
}
SoftwareImageInfo	::= SEQUENCE
{
	minimumDisk				[0] INTEGER OPTIONAL,
	minimumRAM				[1] INTEGER OPTIONAL,
	swImageRef				[2] UTF8String OPTIONAL,
	diskFormat				[3] UTF8String OPTIONAL,
	operatingSystem			[4] UTF8String OPTIONAL
}

SSCMode	::= INTEGER
{
	sSCMode1				(1),
	sSCMode2				(2),
	sSCMode3				(3)
}
-- See 3GPP TS 23.501 [247] for details.

Ssm ::= SEQUENCE 
-- See 3GPP TS 29.571 [249] for details.
{
	sourceIpAddr	[0] IPAddress,
	destIpAddr		[1] IPAddress
}

SteerModeValue	::= ENUMERATED
{
	activeStandby 		(0),
	loadBalancing		(1),
	smallestDelay 		(2),
	priorityBased 		(3)

}


SubscribedQoSInformation	::= SEQUENCE
--
-- See TS 32.291 [58] for more information
-- 
{
	fiveQi				[1] INTEGER OPTIONAL,
	aRP					[2] AllocationRetentionPriority OPTIONAL,
	priorityLevel 		[3] INTEGER OPTIONAL
}


SvcExperience 	::= SEQUENCE
{
	mos					[0] INTEGER OPTIONAL,
	upperRange			[1] INTEGER OPTIONAL,
	lowerRange			[2] INTEGER OPTIONAL
}


SynchronizationState			::= ENUMERATED
{
	locked						(0),
	holdover					(1),
	freerun						(2)
}


-- 
-- T
-- 


TAC			::= OCTET STRING (SIZE(3))

TAI	::= SEQUENCE
{
	pLMNId		[0] PLMN-Id,
	tac			[1] TAC

}

TenantIdentifier			::= OCTET STRING 


Throughput	::= SEQUENCE
{
	guaranteedThpt			[0] Bitrate,
	maximumThpt				[1] Bitrate
}

TimeDistributionMethod			::= ENUMERATED
{
	gPTP				(0),
	aSTI				(1)
}

TimeSource			::= ENUMERATED
--
-- See 3GPP TS 29.571 [249] for details
-- 
{
	pTP						(0),
	gNSS					(1),
	atomicClock				(2),
	terrestrialRadio		(3),
	serialTimeCode			(4),
	nTP						(5),
	handSet					(6),
	other					(7)
}

TimeSynchronizationInformation	::= SEQUENCE
{
	distributionMethod							[1] TimeDistributionMethod OPTIONAL,
	tSNtimeDomainNumber							[2] INTEGER OPTIONAL,
	temporalValidityInformation					[3] CallDuration OPTIONAL,
	spatialValidityInformation					[4] SEQUENCE OF TAI OPTIONAL,
	timeSynchronizationErrorBudget				[5] INTEGER OPTIONAL,
	synchronizationState						[6] SynchronizationState OPTIONAL,
	clockQuality								[7] ClockQuality OPTIONAL,
	parentTimeSource							[8] TimeSource OPTIONAL
}

TNAPId		::= UTF8String
-- 
-- See 3GPP TS 29.571 [249] for details
-- 

TngfId		::= UTF8String

TopologicalLocation		::= SEQUENCE
{
	cellIdList						[0] SEQUENCE OF Ncgi OPTIONAL,
	trackingAreaIdList				[1] SEQUENCE OF TAI OPTIONAL,
	servingPLMN						[2] SEQUENCE OF PLMN-Id
}

-- 
-- See 3GPP TS 29.571 [249] for details
--

TrafficForwardingWay	::= ENUMERATED
{
	n6				(0),
	n19				(1),
	localSwitch		(2)

}


Trigger	::= CHOICE
{
	sMFTrigger		[0] SMFTrigger,
	mBSMFTrigger	[1] MBSMFTrigger,
	nSACFTrigger	[2] NSACFTrigger,
	iMSTrigger	[3] IMSTrigger }

TriggerCategory	::= ENUMERATED
{
	immediateReport		(0),
	deferredReport		(1)
}

TSCAssistanceInformation	::= SEQUENCE
{
	flowDirection							[1] TSCFlowDirection OPTIONAL,
	periodicity								[2] INTEGER OPTIONAL
}


TSCFlowDirection			::= ENUMERATED
{
	uplink				(0),
	downlink			(1)
}

TSNQoSInformation	::= SEQUENCE
{
	priority								[1] INTEGER OPTIONAL,
	bridgeDelay								[2] SEQUENCE OF INTEGER OPTIONAL
}

TWAPId		::= UTF8String
-- 
-- See 3GPP TS 29.571 [249] for details
--

-- 
-- U
-- 

UsedUnitContainer 		::= SEQUENCE
{
	serviceIdentifier					[0] ServiceIdentifier OPTIONAL,
	time								[1] CallDuration OPTIONAL,
	triggers							[2] SEQUENCE OF Trigger OPTIONAL,
	triggerTimeStamp					[3] TimeStamp OPTIONAL,
	dataTotalVolume						[4] DataVolumeOctets OPTIONAL,
	dataVolumeUplink					[5] DataVolumeOctets OPTIONAL,
	dataVolumeDownlink					[6] DataVolumeOctets OPTIONAL,
	serviceSpecificUnits				[7] INTEGER OPTIONAL,
	eventTimeStamp						[8] TimeStamp OPTIONAL,
	localSequenceNumber					[9] LocalSequenceNumber OPTIONAL,
	ratingIndicator						[10] RatingIndicator OPTIONAL,
	pDUContainerInformation				[11] PDUContainerInformation OPTIONAL,
	quotaManagementIndicator			[12] BOOLEAN OPTIONAL,
	quotaManagementIndicatorExt			[13] QuotaManagementIndicator OPTIONAL,
	nSPAContainerInformation			[14] NSPAContainerInformation OPTIONAL,
	eventTimeStampExt					[15] SEQUENCE OF TimeStamp OPTIONAL,
	pC5ContainerInformation				[16] PC5ContainerInformation OPTIONAL,
	mBSContainerInformation				[17] MbsContainerInformation OPTIONAL,
	networkSharingContainerInformation	[18] NetworkSharingContainerInformation OPTIONAL
}

--
-- UserLocationInformationStructured is an alternative ASN.1 format to UserLocationInformation
--

UserLocationInformation	::= OCTET STRING

UserLocationInformationStructured 	::= SEQUENCE
{
	eutraLocation				[0] EutraLocation OPTIONAL,
	nrLocation					[1] NrLocation OPTIONAL,
	n3gaLocation				[2] N3gaLocation OPTIONAL,
	utraLocation				[3] UtraLocation OPTIONAL,
	geraLocation				 [4] GeraLocation OPTIONAL
}

InvolvedPartySatelliteID  		::= SET
{
	callingPartySatelliteID			[0] SatelliteID OPTIONAL,
	calledPartySatelliteID			[1] SatelliteID OPTIONAL
}

UtraLocation	::= SEQUENCE
{
	cgi							[0] CellGlobalId OPTIONAL,
	sai						[1] ServiceAreaId OPTIONAL,
	lai							[2] LocationAreaId OPTIONAL,
	rai						[3] RoutingAreaId OPTIONAL,
	ageOfLocationInformation	[4] AgeOfLocationInformation OPTIONAL,
	ueLocationTimestamp			[5] TimeStamp OPTIONAL,
	geographicalInformation		[6] GeographicalInformation	OPTIONAL,
	geodeticInformation			[7] GeodeticInformation OPTIONAL
}



-- 
-- This data is converted from JSON format of the User Location as described in TS 29.571 [249].
--

-- 
-- V
-- 

VirtualResource	::= SEQUENCE
{
	virtualMemory				[0] INTEGER OPTIONAL,
	virtualDisk					[1] INTEGER OPTIONAL,
	virtualResource				[2] OCTET STRING OPTIONAL
}

VlrNumber	::= UTF8String
-- 
-- See 3GPP TS 29.571 [249] for details
-- 


V2XCommunicationModeIndicator   ::= ENUMERATED
{
	v2XComSupported 			(0),
	v2XComNotSupported			(1)
}

-- 
-- W

WAgfId		::= UTF8String
-- 
-- See 3GPP TS 29.571 [249] for details
--

END
